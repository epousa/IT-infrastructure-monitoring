-- Copyright (C) 2015 by HUAWEI TECHNOLOGIES. All rights reserved.
-- HUAWEI-CGN-MIB.mib
-- Monday, May 07, 2012 at 10:00:00
-- Version:V2.21
	HUAWEI-CGN-MIB DEFINITIONS ::= BEGIN
 
		IMPORTS
			hwDatacomm			
				FROM HUAWEI-MIB			
			OBJECT-GROUP, MODULE-COMPLIANCE, NOTIFICATION-GROUP			
				FROM SNMPv2-CONF			
			TimeTicks, IpAddress, Integer32, Unsigned32, Counter64, 
			BITS, OBJECT-TYPE, MODULE-IDENTITY, NOTIFICATION-TYPE			
				FROM SNMPv2-SMI			
			DisplayString, TruthValue, TEXTUAL-CONVENTION			
				FROM SNMPv2-TC;
	
	
		-- 1.3.6.1.4.1.2011.5.25.306
		hwCGNMIB MODULE-IDENTITY 
			LAST-UPDATED "201508071100Z"  --Aug.7, 2015 at 11:00 GMT
			ORGANIZATION 
				 "Huawei Technologies Co.,Ltd."
			CONTACT-INFO 
				"Huawei Industrial Base

				  Bantian, Longgang

				   Shenzhen 518129

				   People's Republic of China

				   Website: http://www.huawei.com

				   Email: support@huawei.com

				 " 
			 
			DESCRIPTION 
				"The HUAWEI-CGN-MIB contains objects to Manage the CGN 
				configuration.
				"              
                                                                REVISION    "201508071100Z"  --Aug.7, 2015 at 11:00 GMT
                                                                DESCRIPTION  "V2.21, initial version."
                                                               
                                                                REVISION    "201506021600Z"  --June.2, 2015 at 16:00 GMT
                                                                DESCRIPTION  "V2.20, initial version."
																
                                                                REVISION    "201504161143Z"  --Apr.16, 2015 at 11:43 GMT
                                                                DESCRIPTION  "V2.19, initial version."
																
																REVISION    "201502251446Z"  --Feb.25, 2015 at 14:46 GMT				      
																DESCRIPTION "Change the type of leaf node of hwCGNStatisticsPortNumDistrTable ."
																		  
																REVISION    "201412222046Z"  --Dec.22, 2014 at 20:46 GMT				      
																DESCRIPTION "Add a new table for the statistisc of distribution of port usage."

                                                                REVISION    "201410151143Z"  -- Oct.15, 2014 at 11:43 GMT
                                                                DESCRIPTION  "V2.16, initial version."

                                                                REVISION    "201409152106Z"  -- Sep.15, 2014 at 21:06 GMT
                                                                DESCRIPTION  "V2.15, initial version."

                                                                REVISION    "201408211140Z"  -- Aug.21, 2014 at 11:40 GMT
                                                                DESCRIPTION  "V2.14, initial version."
																
                                                                REVISION    "201407081140Z"  -- July.08, 2014 at 11:40 GMT
                                                                DESCRIPTION  "V2.13, initial version."

                                                                REVISION   "201302211530Z"  -- Feb.21, 2013 at 15:30 GMT
                                                                DESCRIPTION  "V2.11, initial version."

                                                                REVISION    "201305221130Z"  -- May.22, 2013 at 11:30 GMT
                                                                DESCRIPTION  "V2.12, initial version."                                              


			::= { hwDatacomm 306 }

		
	
--
-- Textual conventions
--
	
		RowStatus ::= TEXTUAL-CONVENTION
			STATUS current
			DESCRIPTION 
				"The RowStatus textual convention is used to manage the
				creation and deletion of conceptual rows, and is used as the
				value of the SYNTAX clause for the status column of a
				conceptual row (as described in Section 7.7.1 of [2].)
				The status column has six defined values:
				
				     - `active', which indicates that the conceptual row is
				     available for use by the managed device;
				
				     - `notInService', which indicates that the conceptual
				     row exists in the agent, but is unavailable for use by
				     the managed device (see NOTE below); 'notInService' has
				     no implication regarding the internal consistency of
				     the row, availability of resources, or consistency with
				     the current state of the managed device;
				
				     - `notReady', which indicates that the conceptual row
				     exists in the agent, but is missing information
				     necessary in order to be available for use by the
				     managed device (i.e., one or more required columns in
				     the conceptual row have not been instanciated);
				
				     - `createAndGo', which is supplied by a management
				     station wishing to create a new instance of a
				     conceptual row and to have its status automatically set
				     to active, making it available for use by the managed
				     device;
				
				     - `createAndWait', which is supplied by a management
				     station wishing to create a new instance of a
				     conceptual row (but not make it available for use by
				     the managed device); and,
				
				     - `destroy', which is supplied by a management station
				     wishing to delete all of the instances associated with
				     an existing conceptual row.
				
				Whereas five of the six values (all except `notReady') may
				be specified in a management protocol set operation, only
				three values will be returned in response to a management
				protocol retrieval operation:  `notReady', `notInService' or
				`active'.  That is, when queried, an existing conceptual row
				has only three states:  it is either available for use by
				the managed device (the status column has value `active');
				it is not available for use by the managed device, though
				the agent has sufficient information to attempt to make it
				so (the status column has value `notInService'); or, it is
				not available for use by the managed device, and an attempt
				to make it so would fail because the agent has insufficient
				information (the state column has value `notReady').
				                         NOTE WELL
				
				     This textual convention may be used for a MIB table,
				     irrespective of whether the values of that table's
				     conceptual rows are able to be modified while it is
				     active, or whether its conceptual rows must be taken
				     out of service in order to be modified.  That is, it is
				     the responsibility of the DESCRIPTION clause of the
				     status column to specify whether the status column must
				     not be `active' in order for the value of some other
				     column of the same conceptual row to be modified.  If
				     such a specification is made, affected columns may be
				     changed by an SNMP set PDU if the RowStatus would not
				     be equal to `active' either immediately before or after
				     processing the PDU.  In other words, if the PDU also
				     contained a varbind that would change the RowStatus
				     value, the column in question may be changed if the
				     RowStatus was not equal to `active' as the PDU was
				     received, or if the varbind sets the status to a value
				     other than 'active'.
				
				
				Also note that whenever any elements of a row exist, the
				RowStatus column must also exist.
				To summarize the effect of having a conceptual row with a
				status column having a SYNTAX clause value of RowStatus,
				consider the following state diagram:
				
				
				                             STATE
				  +--------------+-----------+-------------+-------------
				  |      A       |     B     |      C      |      D
				  |              |status col.|status column|
				  |status column |    is     |      is     |status column
				ACTION    |does not exist|  notReady | notInService|  is active
				--------------+--------------+-----------+-------------+-------------
				set status    |noError    ->D|inconsist- |inconsistent-|inconsistent-
				column to     |       or     |   entValue|        Value|        Value
				createAndGo   |inconsistent- |           |             |
				  |         Value|           |             |
				--------------+--------------+-----------+-------------+-------------
				set status    |noError  see 1|inconsist- |inconsistent-|inconsistent-
				column to     |       or     |   entValue|        Value|        Value
				createAndWait |wrongValue    |           |             |
				--------------+--------------+-----------+-------------+-------------
				set status    |inconsistent- |inconsist- |noError      |noError
				column to     |         Value|   entValue|             |
				active        |              |           |             |
				  |              |     or    |             |
				  |              |           |             |
				  |              |see 2   ->D|see 8     ->D|          ->D
				--------------+--------------+-----------+-------------+-------------
				set status    |inconsistent- |inconsist- |noError      |noError   ->C
				column to     |         Value|   entValue|             |
				notInService  |              |           |             |
				  |              |     or    |             |      or
				  |              |           |             |
				  |              |see 3   ->C|          ->C|see 6
				--------------+--------------+-----------+-------------+-------------
				set status    |noError       |noError    |noError      |noError   ->A
				column to     |              |           |             |      or
				destroy       |           ->A|        ->A|          ->A|see 7
				--------------+--------------+-----------+-------------+-------------
				set any other |see 4         |noError    |noError      |see 5
				column to some|              |           |             |
				value         |              |      see 1|          ->C|          ->D
				--------------+--------------+-----------+-------------+-------------
				
				(1) goto B or C, depending on information available to the
				agent.
				
				(2) if other variable bindings included in the same PDU,
				provide values for all columns which are missing but
				required, and all columns have acceptable values, then
				return noError and goto D.
				
				(3) if other variable bindings included in the same PDU,
				provide legal values for all columns which are missing but
				required, then return noError and goto C.
				
				(4) at the discretion of the agent, the return value may be
				either:
				
				     inconsistentName:  because the agent does not choose to
				     create such an instance when the corresponding
				     RowStatus instance does not exist, or
				
				     inconsistentValue:  if the supplied value is
				     inconsistent with the state of some other MIB object's
				     value, or
				
				     noError: because the agent chooses to create the
				     instance.
				
				If noError is returned, then the instance of the status
				column must also be created, and the new state is B or C,
				depending on the information available to the agent.  If
				inconsistentName or inconsistentValue is returned, the row
				remains in state A.
				
				(5) depending on the MIB definition for the column/table,
				either noError or inconsistentValue may be returned.
				
				(6) the return value can indicate one of the following
				errors:
				
				     wrongValue: because the agent does not support
				     notInService (e.g., an agent which does not support
				     createAndWait), or
				
				     inconsistentValue: because the agent is unable to take
				     the row out of service at this time, perhaps because it
				     is in use and cannot be de-activated.
				
				(7) the return value can indicate the following error:
				
				     inconsistentValue: because the agent is unable to
				     remove the row at this time, perhaps because it is in
				     use and cannot be de-activated.
				(8) the transition to D can fail, e.g., if the values of the
				conceptual row are inconsistent, then the error code would
				be inconsistentValue.
				
				NOTE: Other processing of (this and other varbinds of) the
				set request may result in a response other than noError
				being returned, e.g., wrongValue, noCreation, etc.
				
				
				                  Conceptual Row Creation
				
				There are four potential interactions when creating a
				conceptual row:  selecting an instance-identifier which is
				not in use; creating the conceptual row; initializing any
				objects for which the agent does not supply a default; and,
				making the conceptual row available for use by the managed
				device.
				
				Interaction 1: Selecting an Instance-Identifier
				
				The algorithm used to select an instance-identifier varies
				for each conceptual row.  In some cases, the instance-
				identifier is semantically significant, e.g., the
				destiCGNion address of a route, and a management station
				selects the instance-identifier according to the semantics.
				
				In other cases, the instance-identifier is used solely to
				distinguish conceptual rows, and a management station
				without specific knowledge of the conceptual row might
				examine the instances present in order to determine an
				unused instance-identifier.  (This approach may be used, but
				it is often highly sub-optimal; however, it is also a
				questionable practice for a naive management station to
				attempt conceptual row creation.)
				
				AlterCGNely, the MIB module which defines the conceptual row
				might provide one or more objects which provide assistance
				in determining an unused instance-identifier.  For example,
				if the conceptual row is indexed by an integer-value, then
				an object having an integer-valued SYNTAX clause might be
				defined for such a purpose, allowing a management station to
				issue a management protocol retrieval operation.  In order
				to avoid unnecessary collisions between competing management
				stations, `adjacent' retrievals of this object should be
				different.
				
				Finally, the management station could select a pseudo-random
				number to use as the index.  In the event that this index
				was already in use and an inconsistentValue was returned in
				response to the management protocol set operation, the
				management station should simply select a new pseudo-random
				number and retry the operation.
				
				A MIB designer should choose between the two latter
				algorithms based on the size of the table (and therefore the
				efficiency of each algorithm).  For tables in which a large
				number of entries are expected, it is recommended that a MIB
				object be defined that returns an acceptable index for
				creation.  For tables with small numbers of entries, it is
				recommended that the latter pseudo-random index mechanism be
				used.
				
				Interaction 2: Creating the Conceptual Row
				
				Once an unused instance-identifier has been selected, the
				management station determines if it wishes to create and
				activate the conceptual row in one transaction or in a
				negotiated set of interactions.
				
				Interaction 2a: Creating and Activating the Conceptual Row
				
				The management station must first determine the column
				requirements, i.e., it must determine those columns for
				which it must or must not provide values.  Depending on the
				complexity of the table and the management station's
				knowledge of the agent's capabilities, this determiCGNion
				can be made locally by the management station.  AlterCGNely,
				the management station issues a management protocol get
				operation to examine all columns in the conceptual row that
				it wishes to create.  In response, for each column, there
				are three possible outcomes:
				
				     - a value is returned, indicating that some other
				     management station has already created this conceptual
				     row.  We return to interaction 1.
				
				     - the exception `noSuchInstance' is returned,
				     indicating that the agent implements the object-type
				     associated with this column, and that this column in at
				     least one conceptual row would be accessible in the MIB
				     view used by the retrieval were it to exist. For those
				     columns to which the agent provides read-create access,
				     the `noSuchInstance' exception tells the management
				     station that it should supply a value for this column
				     when the conceptual row is to be created.
				     - the exception `noSuchObject' is returned, indicating
				     that the agent does not implement the object-type
				     associated with this column or that there is no
				     conceptual row for which this column would be
				     accessible in the MIB view used by the retrieval.  As
				     such, the management station can not issue any
				     management protocol set operations to create an
				     instance of this column.
				
				Once the column requirements have been determined, a
				management protocol set operation is accordingly issued.
				This operation also sets the new instance of the status
				column to `createAndGo'.
				
				When the agent processes the set operation, it verifies that
				it has sufficient information to make the conceptual row
				available for use by the managed device.  The information
				available to the agent is provided by two sources:  the
				management protocol set operation which creates the
				conceptual row, and, implementation-specific defaults
				supplied by the agent (note that an agent must provide
				implementation-specific defaults for at least those objects
				which it implements as read-only).  If there is sufficient
				information available, then the conceptual row is created, a
				`noError' response is returned, the status column is set to
				`active', and no further interactions are necessary (i.e.,
				interactions 3 and 4 are skipped).  If there is insufficient
				information, then the conceptual row is not created, and the
				set operation fails with an error of `inconsistentValue'.
				On this error, the management station can issue a management
				protocol retrieval operation to determine if this was
				because it failed to specify a value for a required column,
				or, because the selected instance of the status column
				already existed.  In the latter case, we return to
				interaction 1.  In the former case, the management station
				can re-issue the set operation with the additional
				information, or begin interaction 2 again using
				`createAndWait' in order to negotiate creation of the
				conceptual row.
				                         NOTE WELL
				
				     Regardless of the method used to determine the column
				     requirements, it is possible that the management
				     station might deem a column necessary when, in fact,
				     the agent will not allow that particular columnar
				     instance to be created or written.  In this case, the
				     management protocol set operation will fail with an
				     error such as `noCreation' or `notWritable'.  In this
				     case, the management station decides whether it needs
				     to be able to set a value for that particular columnar
				     instance.  If not, the management station re-issues the
				     management protocol set operation, but without setting
				     a value for that particular columnar instance;
				     otherwise, the management station aborts the row
				     creation algorithm.
				
				Interaction 2b: Negotiating the Creation of the Conceptual
				Row
				
				The management station issues a management protocol set
				operation which sets the desired instance of the status
				column to `createAndWait'.  If the agent is unwilling to
				process a request of this sort, the set operation fails with
				an error of `wrongValue'.  (As a consequence, such an agent
				must be prepared to accept a single management protocol set
				operation, i.e., interaction 2a above, containing all of the
				columns indicated by its column requirements.)  Otherwise,
				the conceptual row is created, a `noError' response is
				returned, and the status column is immediately set to either
				`notInService' or `notReady', depending on whether it has
				sufficient information to (attempt to) make the conceptual
				row available for use by the managed device.  If there is
				sufficient information available, then the status column is
				set to `notInService'; otherwise, if there is insufficient
				information, then the status column is set to `notReady'.
				Regardless, we proceed to interaction 3.
				
				Interaction 3: Initializing non-defaulted Objects
				
				The management station must now determine the column
				requirements.  It issues a management protocol get operation
				to examine all columns in the created conceptual row.  In
				the response, for each column, there are three possible
				outcomes:
				     - a value is returned, indicating that the agent
				     implements the object-type associated with this column
				     and had sufficient information to provide a value.  For
				     those columns to which the agent provides read-create
				     access (and for which the agent allows their values to
				     be changed after their creation), a value return tells
				     the management station that it may issue additional
				     management protocol set operations, if it desires, in
				     order to change the value associated with this column.
				
				     - the exception `noSuchInstance' is returned,
				     indicating that the agent implements the object-type
				     associated with this column, and that this column in at
				     least one conceptual row would be accessible in the MIB
				     view used by the retrieval were it to exist. However,
				     the agent does not have sufficient information to
				     provide a value, and until a value is provided, the
				     conceptual row may not be made available for use by the
				     managed device.  For those columns to which the agent
				     provides read-create access, the `noSuchInstance'
				     exception tells the management station that it must
				     issue additional management protocol set operations, in
				     order to provide a value associated with this column.
				
				     - the exception `noSuchObject' is returned, indicating
				     that the agent does not implement the object-type
				     associated with this column or that there is no
				     conceptual row for which this column would be
				     accessible in the MIB view used by the retrieval.  As
				     such, the management station can not issue any
				     management protocol set operations to create an
				     instance of this column.
				
				If the value associated with the status column is
				`notReady', then the management station must first deal with
				all `noSuchInstance' columns, if any.  Having done so, the
				value of the status column becomes `notInService', and we
				proceed to interaction 4.
				Interaction 4: Making the Conceptual Row Available
				
				Once the management station is satisfied with the values
				associated with the columns of the conceptual row, it issues
				a management protocol set operation to set the status column
				to `active'.  If the agent has sufficient information to
				make the conceptual row available for use by the managed
				device, the management protocol set operation succeeds (a
				`noError' response is returned).  Otherwise, the management
				protocol set operation fails with an error of
				`inconsistentValue'.
				
				                         NOTE WELL
				
				     A conceptual row having a status column with value
				     `notInService' or `notReady' is unavailable to the
				     managed device.  As such, it is possible for the
				     managed device to create its own instances during the
				     time between the management protocol set operation
				     which sets the status column to `createAndWait' and the
				     management protocol set operation which sets the status
				     column to `active'.  In this case, when the management
				     protocol set operation is issued to set the status
				     column to `active', the values held in the agent
				     supersede those used by the managed device.
				
				If the management station is prevented from setting the
				status column to `active' (e.g., due to management station
				or network failure) the conceptual row will be left in the
				`notInService' or `notReady' state, consuming resources
				indefinitely.  The agent must detect conceptual rows that
				have been in either state for an abnormally long period of
				time and remove them.  It is the responsibility of the
				DESCRIPTION clause of the status column to indicate what an
				abnormally long period of time would be.  This period of
				time should be long enough to allow for human response time
				(including `think time') between the creation of the
				conceptual row and the setting of the status to `active'.
				In the absence of such information in the DESCRIPTION
				clause, it is suggested that this period be approximately 5
				minutes in length.  This removal action applies not only to
				newly-created rows, but also to previously active rows which
				are set to, and left in, the notInService state for a
				prolonged period exceeding that which is considered normal
				for such a conceptual row.
				                 Conceptual Row Suspension
				
				When a conceptual row is `active', the management station
				may issue a management protocol set operation which sets the
				instance of the status column to `notInService'.  If the
				agent is unwilling to do so, the set operation fails with an
				error of `wrongValue' or `inconsistentValue'.  Otherwise,
				the conceptual row is taken out of service, and a `noError'
				response is returned.  It is the responsibility of the
				DESCRIPTION clause of the status column to indicate under
				what circumstances the status column should be taken out of
				service (e.g., in order for the value of some other column
				of the same conceptual row to be modified).
				
				
				                  Conceptual Row Deletion
				
				For deletion of conceptual rows, a management protocol set
				operation is issued which sets the instance of the status
				column to `destroy'.  This request may be made regardless of
				the current value of the status column (e.g., it is possible
				to delete conceptual rows which are either `notReady',
				`notInService' or `active'.)  If the operation succeeds,
				then all instances associated with the conceptual row are
				immediately removed."
			SYNTAX INTEGER
				{
				active(1),
				notInService(2),
				notReady(3),
				createAndGo(4),
				createAndWait(5),
				destroy(6)
				}

	
--
-- Node definitions
--
	
		-- 1.3.6.1.4.1.2011.5.25.306.1
		hwCGNObjects OBJECT IDENTIFIER ::= { hwCGNMIB 1 }
		

		-- 1.3.6.1.4.1.2011.5.25.306.1.1
		hwCGNInstanceTable OBJECT-TYPE
			SYNTAX SEQUENCE OF HwCGNInstanceEntry
			MAX-ACCESS not-accessible
			STATUS current
			DESCRIPTION
				"The hwCGNInstanceTable provides the configuration of CGN instance"
			::= { hwCGNObjects 1 }

		-- 1.3.6.1.4.1.2011.5.25.240.1.1.1
		hwCGNInstanceEntry OBJECT-TYPE
			SYNTAX HwCGNInstanceEntry
			MAX-ACCESS not-accessible
			STATUS current
			DESCRIPTION
				"Description."
			INDEX {  hwCGNCFGInstanceType,
			         hwCGNCFGInstanceIndex }
			::= { hwCGNInstanceTable 1 }		
		
		HwCGNInstanceEntry ::=
			SEQUENCE {
			        hwCGNCFGInstanceType
			                INTEGER,
			        hwCGNCFGInstanceIndex
			                Unsigned32,  
				hwCGNInstanceName
					DisplayString,
				hwCGNSessionLimitState
					INTEGER,
				hwCGNSessionLimitICMPNumber
					Unsigned32,
				hwCGNSessionLimitTCPNumber
					Unsigned32,
				hwCGNSessionLimitUDPNumber
					Unsigned32,
				hwCGNSessionLimitTotalNumber
					Unsigned32,
                                hwCGNPortRangeNumber
                                        Unsigned32
		}
                
                -- 1.3.6.1.4.1.2011.5.25.306.1.1.1.1
                hwCGNCFGInstanceType OBJECT-TYPE
			SYNTAX  INTEGER
                            {
                               nat(0),
                               dslite(1)
                             }   
                        MAX-ACCESS read-only
			STATUS current
			DESCRIPTION
				"Instance type."
			::= { hwCGNInstanceEntry 1 } 
			
		-- 1.3.6.1.4.1.2011.5.25.306.1.1.1.2
		hwCGNCFGInstanceIndex OBJECT-TYPE
			SYNTAX Unsigned32(0..63)
			MAX-ACCESS read-only
			STATUS current
			DESCRIPTION
				"Instance index."
			::= { hwCGNInstanceEntry 2 } 
			               
		-- 1.3.6.1.4.1.2011.5.25.306.1.1.1.3
		hwCGNInstanceName OBJECT-TYPE
			SYNTAX DisplayString (SIZE (1..31))
			MAX-ACCESS read-only
			STATUS current
			DESCRIPTION
				"Instance name."
			::= { hwCGNInstanceEntry 3 }

		
		-- 1.3.6.1.4.1.2011.5.25.306.1.1.1.4
		hwCGNSessionLimitState OBJECT-TYPE
			SYNTAX INTEGER
                           {
                             enable(1),
                             disable(2)
                            }
			MAX-ACCESS read-only
			STATUS current
			DESCRIPTION
				"NAT session limit enable flag."
			::= { hwCGNInstanceEntry 4 }

		
		-- 1.3.6.1.4.1.2011.5.25.306.1.1.1.5
		hwCGNSessionLimitICMPNumber OBJECT-TYPE
			SYNTAX Unsigned32 (50..65535)
			MAX-ACCESS read-only
			STATUS current
			DESCRIPTION
				"ICMP session limit number."
			::= { hwCGNInstanceEntry 5 }

		
		-- 1.3.6.1.4.1.2011.5.25.306.1.1.1.6
		hwCGNSessionLimitTCPNumber OBJECT-TYPE
			SYNTAX Unsigned32 (50..65535)
			MAX-ACCESS read-only
			STATUS current
			DESCRIPTION
				"TCP session limit number."
			::= { hwCGNInstanceEntry 6 }

		
		-- 1.3.6.1.4.1.2011.5.25.306.1.1.1.7
		hwCGNSessionLimitUDPNumber OBJECT-TYPE
			SYNTAX Unsigned32 (50..65535)
			MAX-ACCESS read-only
			STATUS current
			DESCRIPTION
				"UDP session limit number."
			::= { hwCGNInstanceEntry 7 }

		
		-- 1.3.6.1.4.1.2011.5.25.306.1.1.1.8
		hwCGNSessionLimitTotalNumber OBJECT-TYPE
			SYNTAX  Unsigned32 (50..65535)
			MAX-ACCESS read-only
			STATUS current
			DESCRIPTION
				"Total session limit number."
			::= { hwCGNInstanceEntry 8 }

		
		-- 1.3.6.1.4.1.2011.5.25.306.1.1.1.9
		hwCGNPortRangeNumber OBJECT-TYPE
			SYNTAX Unsigned32 
			MAX-ACCESS read-only
			STATUS current
			DESCRIPTION
				"NAT port range number."
			::= { hwCGNInstanceEntry 9 }

             
		-- 1.3.6.1.4.1.2011.5.25.306.1.2
		hwCGNSessionTable OBJECT-TYPE
			SYNTAX SEQUENCE OF HwCGNSessionEntry
			MAX-ACCESS not-accessible
			STATUS current
			DESCRIPTION
				"The hwCGNSessionTable provides the configuration of CGN Session"
			::= { hwCGNObjects 2 }
			
		-- 1.3.6.1.4.1.2011.5.25.306.1.2.1
		hwCGNSessionEntry OBJECT-TYPE
			SYNTAX HwCGNSessionEntry
			MAX-ACCESS not-accessible
			STATUS current
			DESCRIPTION
				"Description."
			INDEX { hwSessionEntPhysicalIndex }
			::= { hwCGNSessionTable 1 }		
		
		HwCGNSessionEntry ::=
			SEQUENCE { 
				hwSessionEntPhysicalIndex
					Unsigned32,
				hwCGNSessionNumber
					Unsigned32
		}
		
		-- 1.3.6.1.4.1.2011.5.25.306.1.2.1.1
		hwSessionEntPhysicalIndex OBJECT-TYPE
			SYNTAX  Unsigned32 
			MAX-ACCESS read-only
			STATUS current
			DESCRIPTION
				"Physical index."
			::= { hwCGNSessionEntry 1 }
					
		-- 1.3.6.1.4.1.2011.5.25.306.1.2.1.2
		hwCGNSessionNumber OBJECT-TYPE
			SYNTAX  Unsigned32
			MAX-ACCESS read-only
			STATUS current
			DESCRIPTION
				"Total session number,unit is M."
			::= { hwCGNSessionEntry 2 }

		-- 1.3.6.1.4.1.2011.5.25.306.1.3
		hwCGNAddressGroupTable OBJECT-TYPE
			SYNTAX SEQUENCE OF  HwCGNAddressGroupEntry
			MAX-ACCESS not-accessible
			STATUS current
			DESCRIPTION
				"The hwCGNAddressGroupTable provides the configuration of CGN address group"
			::= { hwCGNObjects 3 }

		-- 1.3.6.1.4.1.2011.5.25.306.1.3.1
		hwCGNAddressGroupEntry OBJECT-TYPE
			SYNTAX HwCGNAddressGroupEntry
			MAX-ACCESS not-accessible
			STATUS current
			DESCRIPTION
				"Description."
			INDEX { hwCGNInstanceType,
                             hwCGNInstanceIndex,
                             hwCGNAddressGroupIndex}
			::= { hwCGNAddressGroupTable 1 }
					
		HwCGNAddressGroupEntry ::=
			SEQUENCE { 			
				hwCGNInstanceType
					INTEGER,
                                hwCGNInstanceIndex
                                        Unsigned32,
                                hwCGNAddressGroupIndex
                                        Unsigned32,
				hwCGNAddressInstanceName
					DisplayString,
				hwCGNAddressGroupName
					DisplayString,                                        
                                hwCGNAddressGroupUsage
                                        Unsigned32                                        
		        }

 		-- 1.3.6.1.4.1.2011.5.25.306.1.3.1.1
		hwCGNInstanceType OBJECT-TYPE
			SYNTAX  INTEGER
                            {
                               nat(0),
                               dslite(1)
                             }   
			MAX-ACCESS read-only
			STATUS current
			DESCRIPTION
				"Instance type."
			::= { hwCGNAddressGroupEntry 1 }
                
  		-- 1.3.6.1.4.1.2011.5.25.306.1.3.1.2
		hwCGNInstanceIndex OBJECT-TYPE
			SYNTAX  Unsigned32(0..63)
			MAX-ACCESS read-only
			STATUS current
			DESCRIPTION
				"Instance index."
			::= { hwCGNAddressGroupEntry 2 } 
		
  		-- 1.3.6.1.4.1.2011.5.25.306.1.3.1.3
		hwCGNAddressGroupIndex OBJECT-TYPE
			SYNTAX  Unsigned32(0..127)
			MAX-ACCESS read-only
			STATUS current
			DESCRIPTION
				"Address group index."
			::= { hwCGNAddressGroupEntry 3 } 

 		-- 1.3.6.1.4.1.2011.5.25.306.1.3.1.4
		hwCGNAddressInstanceName OBJECT-TYPE
			SYNTAX  DisplayString(SIZE (1..31))
			MAX-ACCESS read-only
			STATUS current
			DESCRIPTION
				"Instance name."
			::= { hwCGNAddressGroupEntry 4 }

 		-- 1.3.6.1.4.1.2011.5.25.306.1.3.1.5
		hwCGNAddressGroupName OBJECT-TYPE
			SYNTAX  DisplayString(SIZE (1..31))
			MAX-ACCESS read-only
			STATUS current
			DESCRIPTION
				"Address group name."
			::= { hwCGNAddressGroupEntry 5 }
			
 		-- 1.3.6.1.4.1.2011.5.25.306.1.3.1.6
		hwCGNAddressGroupUsage OBJECT-TYPE
			SYNTAX  Unsigned32(0..100)
			MAX-ACCESS read-only
			STATUS current
			DESCRIPTION
				"Address group usage."
			::= { hwCGNAddressGroupEntry 6 }
									
		-- 1.3.6.1.4.1.2011.5.25.306.1.4
		hwCGNUserPortInformationTable OBJECT-TYPE
			SYNTAX SEQUENCE OF  HwCGNUserPortInformationEntry
			MAX-ACCESS not-accessible
			STATUS current
			DESCRIPTION
				"The hwCGNUserPortInformationTable provides the configuration of CGN user port."			
			::= { hwCGNObjects 4 }

		-- 1.3.6.1.4.1.2011.5.25.240.1.4.1
		hwCGNUserPortInformationEntry OBJECT-TYPE
			SYNTAX HwCGNUserPortInformationEntry
			MAX-ACCESS not-accessible
			STATUS current
			DESCRIPTION
				"Description."
			INDEX {hwCGNPortUserId }
			::= { hwCGNUserPortInformationTable 1 }

		
		HwCGNUserPortInformationEntry ::=
			SEQUENCE {
                           hwCGNPortUserId
                               Unsigned32 ,
                           hwCGNUserPortICMPNumber
                               Unsigned32 ,
                           hwCGNUserPortTCPNumber
                               Unsigned32 ,
                           hwCGNUserPortUDPNumber
                               Unsigned32 ,
                           hwCGNUserPortTotalNumber                   
                               Unsigned32 
                      }
 
 		-- 1.3.6.1.4.1.2011.5.25.306.1.4.1.1
		hwCGNPortUserId OBJECT-TYPE
			SYNTAX  Unsigned32(0..279551)
			MAX-ACCESS read-only
			STATUS current
			DESCRIPTION
				"User ID."
			::= { hwCGNUserPortInformationEntry 1 }
             
 		-- 1.3.6.1.4.1.2011.5.25.306.1.4.1.2
		hwCGNUserPortICMPNumber OBJECT-TYPE
			SYNTAX  Unsigned32
			MAX-ACCESS read-only
			STATUS current
			DESCRIPTION
				"User port ICMP number."
			::= { hwCGNUserPortInformationEntry 2 }

 		-- 1.3.6.1.4.1.2011.5.25.306.1.4.1.3
		hwCGNUserPortTCPNumber OBJECT-TYPE
			SYNTAX  Unsigned32
			MAX-ACCESS read-only
			STATUS current
			DESCRIPTION
				"User port TCP number."
			::= { hwCGNUserPortInformationEntry 3 }

 		-- 1.3.6.1.4.1.2011.5.25.306.1.4.1.4
		hwCGNUserPortUDPNumber OBJECT-TYPE
			SYNTAX  Unsigned32
			MAX-ACCESS read-only
			STATUS current
			DESCRIPTION
				"User port UDP number."
			::= { hwCGNUserPortInformationEntry 4 }	

 		-- 1.3.6.1.4.1.2011.5.25.306.1.4.1.5
		hwCGNUserPortTotalNumber OBJECT-TYPE
			SYNTAX  Unsigned32
			MAX-ACCESS read-only
			STATUS current
			DESCRIPTION
				"User port total number."
			::= { hwCGNUserPortInformationEntry 5 }	

		-- 1.3.6.1.4.1.2011.5.25.306.1.5
		hwCGNUserSessionInformationTable OBJECT-TYPE
			SYNTAX SEQUENCE OF  HwCGNUserSessionInformationEntry
			MAX-ACCESS not-accessible
			STATUS current
			DESCRIPTION
				"The hwCGNUserSessionInformationTable provides the configuration of CGN user session"
			::= { hwCGNObjects 5 }
			
		-- 1.3.6.1.4.1.2011.5.25.240.1.5.1
		hwCGNUserSessionInformationEntry OBJECT-TYPE
			SYNTAX HwCGNUserSessionInformationEntry
			MAX-ACCESS not-accessible
			STATUS current
			DESCRIPTION
				"Description."
			INDEX {hwCGNSessionUserId}
			::= { hwCGNUserSessionInformationTable 1 }
		
		HwCGNUserSessionInformationEntry ::=
			SEQUENCE {
                      hwCGNSessionUserId
                         Unsigned32,
                      hwCGNUserSessionICMPNumber
                         Unsigned32,
                      hwCGNUserSessionTCPNumber
                         Unsigned32,
                      hwCGNUserSessionUDPNumber
                         Unsigned32,
                      hwCGNUserSessionTOTALNumber
                         Unsigned32,
                      hwCGNUserRevSessionICMPNumber
                         Unsigned32,
                      hwCGNUserRevSessionTCPNumber
                         Unsigned32, 
                      hwCGNUserRevSessionUDPNumber
                         Unsigned32                  
                   }

 		-- 1.3.6.1.4.1.2011.5.25.306.1.5.1.1
		hwCGNSessionUserId OBJECT-TYPE
			SYNTAX  Unsigned32(0..279551)
			MAX-ACCESS read-only
			STATUS current
			DESCRIPTION
				"User ID."
			::= { hwCGNUserSessionInformationEntry 1 }	

 		-- 1.3.6.1.4.1.2011.5.25.306.1.5.1.2
		hwCGNUserSessionICMPNumber OBJECT-TYPE
			SYNTAX  Unsigned32
			MAX-ACCESS read-only
			STATUS current
			DESCRIPTION
				"User session ICMP number"
			::= { hwCGNUserSessionInformationEntry 2 }	

 		-- 1.3.6.1.4.1.2011.5.25.306.1.5.1.3
		hwCGNUserSessionTCPNumber OBJECT-TYPE
			SYNTAX  Unsigned32
			MAX-ACCESS read-only
			STATUS current
			DESCRIPTION
				"User session TCP number."
			::= { hwCGNUserSessionInformationEntry 3 }	

 		-- 1.3.6.1.4.1.2011.5.25.306.1.5.1.4
		hwCGNUserSessionUDPNumber OBJECT-TYPE
			SYNTAX  Unsigned32
			MAX-ACCESS read-only
			STATUS current
			DESCRIPTION
				"User session UDP number."
			::= { hwCGNUserSessionInformationEntry 4 }	

 		-- 1.3.6.1.4.1.2011.5.25.306.1.5.1.5
		hwCGNUserSessionTOTALNumber OBJECT-TYPE
			SYNTAX  Unsigned32
			MAX-ACCESS read-only
			STATUS current
			DESCRIPTION
				"User session total number."
			::= { hwCGNUserSessionInformationEntry 5 }	

 		-- 1.3.6.1.4.1.2011.5.25.306.1.5.1.6
		hwCGNUserRevSessionICMPNumber OBJECT-TYPE
			SYNTAX  Unsigned32
			MAX-ACCESS read-only
			STATUS current
			DESCRIPTION
				"Reverse user session ICMP number."
			::= { hwCGNUserSessionInformationEntry 6 }	

 		-- 1.3.6.1.4.1.2011.5.25.306.1.5.1.7
		hwCGNUserRevSessionTCPNumber OBJECT-TYPE
			SYNTAX  Unsigned32
			MAX-ACCESS read-only
			STATUS current
			DESCRIPTION
				"Reverse user session TCP number."
			::= { hwCGNUserSessionInformationEntry 7 }	

 		-- 1.3.6.1.4.1.2011.5.25.306.1.5.1.8
		hwCGNUserRevSessionUDPNumber OBJECT-TYPE
			SYNTAX  Unsigned32
			MAX-ACCESS read-only
			STATUS current
			DESCRIPTION
				"Reverse user session UDP number."
			::= { hwCGNUserSessionInformationEntry 8 }	

		-- 1.3.6.1.4.1.2011.5.25.306.1.6
		hwCGNDsliteTunnelTable OBJECT-TYPE
			SYNTAX SEQUENCE OF  HwCGNDsliteTunnelEntry
			MAX-ACCESS not-accessible
			STATUS current
			DESCRIPTION
				"The hwCGNDsliteTunnelTable provides the configuration of DS-LITE tunnel"
			::= { hwCGNObjects 6 }

		-- 1.3.6.1.4.1.2011.5.25.240.1.6.1
		hwCGNDsliteTunnelEntry OBJECT-TYPE
			SYNTAX HwCGNDsliteTunnelEntry
			MAX-ACCESS not-accessible
			STATUS current
			DESCRIPTION
				"Description."
			INDEX {hwTunnelEntPhysicalIndex}
			::= { hwCGNDsliteTunnelTable 1 }
		
		HwCGNDsliteTunnelEntry ::=
			SEQUENCE {
                        hwTunnelEntPhysicalIndex
                           Unsigned32,
                        hwCGNCurTunnelNumber
                           Counter64
                    }

  		-- 1.3.6.1.4.1.2011.5.25.306.1.6.1.1
		hwTunnelEntPhysicalIndex OBJECT-TYPE
			SYNTAX  Unsigned32
			MAX-ACCESS read-only
			STATUS current
			DESCRIPTION
				"Physical index."
			::= { hwCGNDsliteTunnelEntry 1 }	

  		-- 1.3.6.1.4.1.2011.5.25.306.1.6.1.2
		hwCGNCurTunnelNumber OBJECT-TYPE
			SYNTAX  Counter64
			MAX-ACCESS read-only
			STATUS current
			DESCRIPTION
				"Current tunnel number."
			::= { hwCGNDsliteTunnelEntry 2 }	

		-- 1.3.6.1.4.1.2011.5.25.306.1.7
		hwCGNTransmitAbilityTable OBJECT-TYPE
			SYNTAX SEQUENCE OF  HwCGNTransmitAbilityEntry
			MAX-ACCESS not-accessible
			STATUS current
			DESCRIPTION
				"The hwCGNTransmitAbilityTable provides the configuration of CGN transmit"
			::= { hwCGNObjects 7 }
		
		-- 1.3.6.1.4.1.2011.5.25.240.1.7.1
		hwCGNTransmitAbilityEntry OBJECT-TYPE
			SYNTAX HwCGNTransmitAbilityEntry
			MAX-ACCESS not-accessible
			STATUS current
			DESCRIPTION
				"Description."
			INDEX {hwEntPhysicalIndex}
			::= { hwCGNTransmitAbilityTable 1 }
		
		HwCGNTransmitAbilityEntry ::=
			SEQUENCE {
                      hwEntPhysicalIndex
                         Unsigned32,
                      hwCGNTotalPacketForwardingThroughput
                         Counter64,
                      hwCGNTotalBitForwardingThroughput
                         Counter64,  
                      hwCGNTotalPacketRevForwardingThroughput
                         Counter64,
                      hwCGNTotalBitRevForwardingThroughput
                         Counter64, 
                      hwCGNTotalFlowSetupRate 
                         Counter64,
                      hwCGNTotalRevFlowSetupRate 
                         Counter64                       
                     }

  		-- 1.3.6.1.4.1.2011.5.25.306.1.7.1.1
		   hwEntPhysicalIndex OBJECT-TYPE
			SYNTAX  Unsigned32
			MAX-ACCESS read-only
			STATUS current
			DESCRIPTION
				"Physical index."
			::= { hwCGNTransmitAbilityEntry 1 }
			
  		-- 1.3.6.1.4.1.2011.5.25.306.1.7.1.3
		   hwCGNTotalPacketForwardingThroughput OBJECT-TYPE
			SYNTAX  Counter64
			MAX-ACCESS read-only
			STATUS current
			DESCRIPTION
				"Total packet forwarding throughput number."
			::= { hwCGNTransmitAbilityEntry 2 }

  		-- 1.3.6.1.4.1.2011.5.25.306.1.7.1.4
		   hwCGNTotalBitForwardingThroughput OBJECT-TYPE
			SYNTAX  Counter64
			MAX-ACCESS read-only
			STATUS current
			DESCRIPTION
				"Total bit forwarding throughput number."
			::= { hwCGNTransmitAbilityEntry 3 }
		
  		-- 1.3.6.1.4.1.2011.5.25.306.1.7.1.5
		   hwCGNTotalPacketRevForwardingThroughput OBJECT-TYPE
			SYNTAX  Counter64
			MAX-ACCESS read-only
			STATUS current
			DESCRIPTION
				"Total packet reverse forwarding throughput number."
			::= { hwCGNTransmitAbilityEntry 4 }

  		-- 1.3.6.1.4.1.2011.5.25.306.1.7.1.6
		   hwCGNTotalBitRevForwardingThroughput OBJECT-TYPE
			SYNTAX  Counter64
			MAX-ACCESS read-only
			STATUS current
			DESCRIPTION
				"Total bit reverse forwarding throughput number."
			::= { hwCGNTransmitAbilityEntry 5 }
									
  		-- 1.3.6.1.4.1.2011.5.25.306.1.7.1.7
		   hwCGNTotalFlowSetupRate  OBJECT-TYPE
			SYNTAX  Counter64
			MAX-ACCESS read-only
			STATUS current
			DESCRIPTION
				"Total flow setup rate."
			::= { hwCGNTransmitAbilityEntry 6 }
		
  		-- 1.3.6.1.4.1.2011.5.25.306.1.7.1.7
		   hwCGNTotalRevFlowSetupRate  OBJECT-TYPE
			SYNTAX  Counter64
			MAX-ACCESS read-only
			STATUS current
			DESCRIPTION
				"Total reverse flow setup rate."
			::= { hwCGNTransmitAbilityEntry 7 }	

		-- 1.3.6.1.4.1.2011.5.25.306.1.8
		hwCGNCurrentSessionTable OBJECT-TYPE
			SYNTAX SEQUENCE OF  HwCGNCurrentSessionEntry
			MAX-ACCESS not-accessible
			STATUS current
			DESCRIPTION
				"The current session table"
			::= { hwCGNObjects 8 }

		-- 1.3.6.1.4.1.2011.5.25.240.1.8.1
		hwCGNCurrentSessionEntry OBJECT-TYPE
			SYNTAX HwCGNCurrentSessionEntry
			MAX-ACCESS not-accessible
			STATUS current
			DESCRIPTION
				"Description."
			INDEX {hwCurSessionEntPhysicalIndex}
			::= { hwCGNCurrentSessionTable 1 }
		
		HwCGNCurrentSessionEntry ::=
			SEQUENCE {
                        hwCurSessionEntPhysicalIndex
                           Unsigned32,
                        hwCGNCurSessionNumber
                           Counter64
                    }

  		-- 1.3.6.1.4.1.2011.5.25.306.1.8.1.1
		hwCurSessionEntPhysicalIndex OBJECT-TYPE
			SYNTAX  Unsigned32
			MAX-ACCESS read-only
			STATUS current
			DESCRIPTION
				"Physical index."
			::= { hwCGNCurrentSessionEntry 1 }	

  		-- 1.3.6.1.4.1.2011.5.25.306.1.8.1.2
		hwCGNCurSessionNumber OBJECT-TYPE
			SYNTAX  Counter64
			MAX-ACCESS read-only
			STATUS current
			DESCRIPTION
				"Current session number."
			::= { hwCGNCurrentSessionEntry 2 }

		-- 1.3.6.1.4.1.2011.5.25.306.1.9
		hwCGNAddressGroupInfoTable OBJECT-TYPE
			SYNTAX SEQUENCE OF  HwCGNAddressGroupInfoEntry
			MAX-ACCESS not-accessible
			STATUS current
			DESCRIPTION
				"The hwCGNAddressGroupTable provides the configuration of CGN address group"
			::= { hwCGNObjects 9 }

		-- 1.3.6.1.4.1.2011.5.25.306.1.9.1
		hwCGNAddressGroupInfoEntry OBJECT-TYPE
			SYNTAX HwCGNAddressGroupInfoEntry
			MAX-ACCESS not-accessible
			STATUS current
			DESCRIPTION
				"Description."
			INDEX { 
			     hwCGNAddressInstanceType,
                             hwCGNAddressInstanceIndex,
                             hwCGNAddressIndex,
                             hwCGNAddressSectionId
                             }
			::= { hwCGNAddressGroupInfoTable 1 }
					
		HwCGNAddressGroupInfoEntry ::=
			SEQUENCE { 
				hwCGNAddressInstanceType
				     INTEGER,
                                hwCGNAddressInstanceIndex
                                     Unsigned32,
                                hwCGNAddressIndex
                                     Unsigned32,
                                hwCGNAddressSectionId
                                     Unsigned32,                               
                                hwCGNAddressGroupStartAddr
                                        DisplayString,
                                hwCGNAddressGroupEndAddr
                                        DisplayString,
                                hwCGNAddressGroupMaskAddr
                                        DisplayString,                                       
                                hwCGNAddressGroupMaskNumber
                                        Unsigned32,
                                hwCGNAddressVPNInstanceName
                                        DisplayString                                                                                                         
                               }
 
  		-- 1.3.6.1.4.1.2011.5.25.306.1.9.1.1
		hwCGNAddressInstanceType OBJECT-TYPE
			SYNTAX  INTEGER
			        {
	                             nat(0),
	                             dslite(1)			        
			        }
			MAX-ACCESS read-only
			STATUS current
			DESCRIPTION
				"Instance type,NAT or ds-lite."
			::= { hwCGNAddressGroupInfoEntry 1 }
 
 		hwCGNAddressInstanceIndex OBJECT-TYPE
			SYNTAX  Unsigned32(0..63)
			MAX-ACCESS read-only
			STATUS current
			DESCRIPTION
				"NAT or ds-lite instance index"
			::= { hwCGNAddressGroupInfoEntry 2 }
 
  		hwCGNAddressIndex OBJECT-TYPE
			SYNTAX  Unsigned32(0..127)
			MAX-ACCESS read-only
			STATUS current
			DESCRIPTION
				"Address group index"
			::= { hwCGNAddressGroupInfoEntry 3 }
			
  		hwCGNAddressSectionId OBJECT-TYPE
			SYNTAX  Unsigned32(0..15 | 255)
			MAX-ACCESS read-only
			STATUS current
			DESCRIPTION
				"Address group section ID"
			::= { hwCGNAddressGroupInfoEntry 4 }			
                               
   		hwCGNAddressGroupStartAddr OBJECT-TYPE
			SYNTAX  DisplayString(SIZE (0..31))
			MAX-ACCESS read-only
			STATUS current
			DESCRIPTION
				"Address group start address"
			::= { hwCGNAddressGroupInfoEntry 5 }  
   
    		hwCGNAddressGroupEndAddr OBJECT-TYPE
			SYNTAX  DisplayString(SIZE (0..31))
			MAX-ACCESS read-only
			STATUS current
			DESCRIPTION
				"Address group end address"
			::= { hwCGNAddressGroupInfoEntry 6 }    
   
     		hwCGNAddressGroupMaskAddr OBJECT-TYPE
			SYNTAX  DisplayString(SIZE (0..31))
			MAX-ACCESS read-only
			STATUS current
			DESCRIPTION
				"Address group mask address"
			::= { hwCGNAddressGroupInfoEntry 7 }      
  
      		hwCGNAddressGroupMaskNumber OBJECT-TYPE
			SYNTAX  Unsigned32(0..32)
			MAX-ACCESS read-only
			STATUS current
			DESCRIPTION
				"Address group mask number"
			::= { hwCGNAddressGroupInfoEntry 8 } 
               
       	        hwCGNAddressVPNInstanceName OBJECT-TYPE
       	        	SYNTAX  DisplayString(SIZE (0..31))
			MAX-ACCESS read-only
			STATUS current
			DESCRIPTION
				"Address group VPN instance name."
			::= { hwCGNAddressGroupInfoEntry 9 }
			
		-- 1.3.6.1.4.1.2011.5.25.306.1.10
		hwCGNStatisticsInfoTable OBJECT-TYPE
			SYNTAX SEQUENCE OF  HwCGNStatisticsInfoEntry
			MAX-ACCESS not-accessible
			STATUS current
			DESCRIPTION
				"NAT statistics information table"
			::= { hwCGNObjects 10 }

		-- 1.3.6.1.4.1.2011.5.25.240.1.9.1
		hwCGNStatisticsInfoEntry OBJECT-TYPE
			SYNTAX HwCGNStatisticsInfoEntry
			MAX-ACCESS not-accessible
			STATUS current
			DESCRIPTION
				"Description."
			INDEX {hwCGNEntPhysicalIndex}
			::= { hwCGNStatisticsInfoTable 1 }
		
		HwCGNStatisticsInfoEntry ::=
			SEQUENCE {
                        hwCGNEntPhysicalIndex
                           Unsigned32,                                                 
                        hwCGNDiscardNumber
                           Counter64,
                        hwCGNErrorNumber
                           Counter64, 
                        hwCGNServermapNumber
                           Counter64,                                                 
                        hwCGNFragSSNNumber
                           Counter64,
                        hwCGNNat444SessionNumber
                           Counter64,
                        hwCGNDsliteSessionNumber
                           Counter64, 
                        hwCGNReceivedPacket
                           Counter64,
                        hwCGNTransmittedPacket
                           Counter64, 
                        hwCGNSessionTableNumber
                           Counter64,
                        hwCGNUserTableNumber
                           Counter64,
						--modified
						hwCGNNat64SessionNumber
							Counter64,
						hwCGNPCPSessionNumber
							Counter64,
						hwCGNPCPNAT444SessionNumber
							Counter64,
						hwCGNPCPDSLITESessionNumber
							Counter64,
						hwCGNPCPLAFT6SessionNumber
							Counter64,
						hwCGNCurrentSessionSpeed
							Counter64,
						hwCGNTotalSetupSession
							Counter64,
						hwCGNTotalTearDownSession
							Counter64				
						--modified						
                    }

   		-- 1.3.6.1.4.1.2011.5.25.306.1.9.1.1
		hwCGNEntPhysicalIndex OBJECT-TYPE
			SYNTAX     Unsigned32
			MAX-ACCESS read-only
			STATUS current
			DESCRIPTION
				"Physical index."
			::= { hwCGNStatisticsInfoEntry 1 }
			               
  		-- 1.3.6.1.4.1.2011.5.25.306.1.9.1.2
		hwCGNDiscardNumber OBJECT-TYPE
			SYNTAX     Counter64
			MAX-ACCESS read-only
			STATUS current
			DESCRIPTION
				"NAT discard number."
			::= { hwCGNStatisticsInfoEntry 2 }

  		-- 1.3.6.1.4.1.2011.5.25.306.1.9.1.3
		hwCGNErrorNumber OBJECT-TYPE
			SYNTAX     Counter64
			MAX-ACCESS read-only
			STATUS current
			DESCRIPTION
				"NAT error number."
			::= { hwCGNStatisticsInfoEntry 3 }
			
  		-- 1.3.6.1.4.1.2011.5.25.306.1.9.1.4
		hwCGNServermapNumber OBJECT-TYPE
			SYNTAX     Counter64
			MAX-ACCESS read-only
			STATUS current
			DESCRIPTION
				"Server-map number."
			::= { hwCGNStatisticsInfoEntry 4 }
			
  		-- 1.3.6.1.4.1.2011.5.25.306.1.9.1.5
		hwCGNFragSSNNumber OBJECT-TYPE
			SYNTAX     Counter64
			MAX-ACCESS read-only
			STATUS current
			DESCRIPTION
				"Frag SSN number."
			::= { hwCGNStatisticsInfoEntry 5 }			
			
  		-- 1.3.6.1.4.1.2011.5.25.306.1.9.1.6
		hwCGNNat444SessionNumber OBJECT-TYPE
			SYNTAX     Counter64
			MAX-ACCESS read-only
			STATUS current
			DESCRIPTION
				"NAT444 session number."
			::= { hwCGNStatisticsInfoEntry 6 }
									
  		-- 1.3.6.1.4.1.2011.5.25.306.1.9.1.7
		hwCGNDsliteSessionNumber OBJECT-TYPE
			SYNTAX     Counter64
			MAX-ACCESS read-only
			STATUS current
			DESCRIPTION
				"Ds-lite session number."
			::= { hwCGNStatisticsInfoEntry 7 }
			
  		-- 1.3.6.1.4.1.2011.5.25.306.1.9.1.8
		hwCGNReceivedPacket OBJECT-TYPE
			SYNTAX     Counter64
			MAX-ACCESS read-only
			STATUS current
			DESCRIPTION
				"NAT Packets received from interface."
			::= { hwCGNStatisticsInfoEntry 8 }

  		-- 1.3.6.1.4.1.2011.5.25.306.1.9.1.9
		hwCGNTransmittedPacket OBJECT-TYPE
			SYNTAX     Counter64
			MAX-ACCESS read-only
			STATUS current
			DESCRIPTION
				"NAT Packets transmitted to interface."
			::= { hwCGNStatisticsInfoEntry 9 }

  		-- 1.3.6.1.4.1.2011.5.25.306.1.9.1.10
		hwCGNSessionTableNumber OBJECT-TYPE
			SYNTAX     Counter64
			MAX-ACCESS read-only
			STATUS current
			DESCRIPTION
				"NAT session table number."
			::= { hwCGNStatisticsInfoEntry 10 }

  		-- 1.3.6.1.4.1.2011.5.25.306.1.9.1.11
		hwCGNUserTableNumber OBJECT-TYPE
			SYNTAX     Counter64
			MAX-ACCESS read-only
			STATUS current
			DESCRIPTION
				"NAT user table number."
			::= { hwCGNStatisticsInfoEntry 11 }
												
		--modified
		hwCGNNat64SessionNumber OBJECT-TYPE
			SYNTAX     Counter64
			MAX-ACCESS read-only
			STATUS current
			DESCRIPTION
				"Total current nat64 sessions in Memory."
			::= { hwCGNStatisticsInfoEntry 12 }
		hwCGNPCPSessionNumber OBJECT-TYPE
			SYNTAX     Counter64
			MAX-ACCESS read-only
			STATUS current
			DESCRIPTION
				"Total current PCP sessions in Memory."
			::= { hwCGNStatisticsInfoEntry 13 }
		hwCGNPCPNAT444SessionNumber OBJECT-TYPE
			SYNTAX     Counter64
			MAX-ACCESS read-only
			STATUS current
			DESCRIPTION
				"Current PCP sessions from NAT444 in Memory."
			::= { hwCGNStatisticsInfoEntry 14 }
		hwCGNPCPDSLITESessionNumber OBJECT-TYPE
			SYNTAX     Counter64
			MAX-ACCESS read-only
			STATUS current
			DESCRIPTION
				"Current PCP sessions from DSLITE in Memory."
			::= { hwCGNStatisticsInfoEntry 15 }
		hwCGNPCPLAFT6SessionNumber OBJECT-TYPE
			SYNTAX     Counter64
			MAX-ACCESS read-only
			STATUS current
			DESCRIPTION
				"Current PCP sessions from LAFT6 in Memory."
			::= { hwCGNStatisticsInfoEntry 16 }
		hwCGNCurrentSessionSpeed OBJECT-TYPE
			SYNTAX     Counter64
			MAX-ACCESS read-only
			STATUS current
			DESCRIPTION
				"Current session speed."
			::= { hwCGNStatisticsInfoEntry 17 }
		hwCGNTotalSetupSession OBJECT-TYPE
			SYNTAX     Counter64
			MAX-ACCESS read-only
			STATUS current
			DESCRIPTION
				"Total setup sessions."
			::= { hwCGNStatisticsInfoEntry 18 }
		hwCGNTotalTearDownSession OBJECT-TYPE
			SYNTAX     Counter64
			MAX-ACCESS read-only
			STATUS current
			DESCRIPTION
				"Total teardown sessions."
			::= { hwCGNStatisticsInfoEntry 19 }			
												
		--modified
												
		-- 1.3.6.1.4.1.2011.5.25.306.1.11
		hwCGNBandwidthTable OBJECT-TYPE
			SYNTAX SEQUENCE OF HwCGNBandwidthEntry
			MAX-ACCESS not-accessible
			STATUS current
			DESCRIPTION
				"The hwCGNSessionTable provides the configuration of CGN bandwidth"
			::= { hwCGNObjects 11 }
			
		-- 1.3.6.1.4.1.2011.5.25.306.1.11.1
		hwCGNBandwidthEntry OBJECT-TYPE
			SYNTAX HwCGNBandwidthEntry
			MAX-ACCESS not-accessible
			STATUS current
			DESCRIPTION
				"Description."
			INDEX { hwBandwidthEntPhysicalIndex }
			::= { hwCGNBandwidthTable 1 }		
		
		HwCGNBandwidthEntry ::=
			SEQUENCE { 
				hwBandwidthEntPhysicalIndex
					Unsigned32,
				hwCGNBandwidthNumber
					Counter64
		}
		
		-- 1.3.6.1.4.1.2011.5.25.306.1.11.1.1
		hwBandwidthEntPhysicalIndex OBJECT-TYPE
			SYNTAX  Unsigned32 
			MAX-ACCESS read-only
			STATUS current
			DESCRIPTION
				"Physical index."
			::= { hwCGNBandwidthEntry 1 }
					
		-- 1.3.6.1.4.1.2011.5.25.306.1.11.1.2
		hwCGNBandwidthNumber OBJECT-TYPE
			SYNTAX  Counter64
			MAX-ACCESS read-only
			STATUS current
			DESCRIPTION
				"Bandwidth number,unit is G."
			::= { hwCGNBandwidthEntry 2 }

		-- 1.3.6.1.4.1.2011.5.25.306.1.12
		hwCGNBoardScalarTable OBJECT-TYPE
			SYNTAX SEQUENCE OF HwCGNBoardScalarEntry
			MAX-ACCESS not-accessible
			STATUS current
			DESCRIPTION
				"The hwCGNSessionTable provides the configuration of CGN bandwidth"
			::= { hwCGNObjects 12 }
			
		-- 1.3.6.1.4.1.2011.5.25.306.1.11.1
		hwCGNBoardScalarEntry OBJECT-TYPE
			SYNTAX HwCGNBoardScalarEntry
			MAX-ACCESS not-accessible
			STATUS current
			DESCRIPTION
				"Description."
			INDEX { hwCGNBoardSlotIndex }
			::= { hwCGNBoardScalarTable 1 }		
		
		HwCGNBoardScalarEntry ::=
			SEQUENCE { 
				hwCGNBoardSlotIndex
					Unsigned32,
				hwCGNBoardSessionNumber
					Counter64,
				hwCGNBoardCurSessionNumber
				        Counter64,
				hwCGNBoardPacketThoughputNumber
				        Counter64,
				hwCGNBoardBitThoughputNumber
				        Counter64,
				hwCGNBoardRevPacketThoughputNumber
				        Counter64,
				hwCGNBoardRevBitThoughputNumber
				        Counter64,
				hwCGNBoardFlowSetupNumber
				        Counter64,
				hwCGNBoardRevFlowSetupNumber
				        Counter64,							        				
				hwCGNBoardBandwidthNumber
				        Counter64,
				hwCGNBoardDsliteTunnelNumber
				        Counter64
		}

		-- 1.3.6.1.4.1.2011.5.25.306.1.12.1.1
		hwCGNBoardSlotIndex OBJECT-TYPE
			SYNTAX  Unsigned32
			MAX-ACCESS read-only
			STATUS current
			DESCRIPTION
				"Slot index."
			::= { hwCGNBoardScalarEntry 1 }
					
		-- 1.3.6.1.4.1.2011.5.25.306.1.12.1.2
		hwCGNBoardSessionNumber OBJECT-TYPE
			SYNTAX  Counter64
			MAX-ACCESS read-only
			STATUS current
			DESCRIPTION
				"Board session number,unit is M"
			::= { hwCGNBoardScalarEntry 2 }

		-- 1.3.6.1.4.1.2011.5.25.306.1.12.1.3
		hwCGNBoardCurSessionNumber OBJECT-TYPE
			SYNTAX  Counter64
			MAX-ACCESS read-only
			STATUS current
			DESCRIPTION
				"Board current session number."
			::= { hwCGNBoardScalarEntry 3 }

		-- 1.3.6.1.4.1.2011.5.25.306.1.12.1.4
		hwCGNBoardPacketThoughputNumber OBJECT-TYPE
			SYNTAX  Counter64
			MAX-ACCESS read-only
			STATUS current
			DESCRIPTION
				"Board packet thoughput number."
			::= { hwCGNBoardScalarEntry 4 }

		-- 1.3.6.1.4.1.2011.5.25.306.1.12.1.5
		hwCGNBoardBitThoughputNumber OBJECT-TYPE
			SYNTAX  Counter64
			MAX-ACCESS read-only
			STATUS current
			DESCRIPTION
				"Board reverse packet thoughput number."
			::= { hwCGNBoardScalarEntry 5 }

		-- 1.3.6.1.4.1.2011.5.25.306.1.12.1.6
		hwCGNBoardRevPacketThoughputNumber OBJECT-TYPE
			SYNTAX  Counter64
			MAX-ACCESS read-only
			STATUS current
			DESCRIPTION
				"Board bit thoughput number."
			::= { hwCGNBoardScalarEntry 6 }
			
		-- 1.3.6.1.4.1.2011.5.25.306.1.12.1.7
		hwCGNBoardRevBitThoughputNumber OBJECT-TYPE
			SYNTAX  Counter64
			MAX-ACCESS read-only
			STATUS current
			DESCRIPTION
				"Board reverse bit thoughput number."
			::= { hwCGNBoardScalarEntry 7 }

		-- 1.3.6.1.4.1.2011.5.25.306.1.12.1.8
		hwCGNBoardFlowSetupNumber OBJECT-TYPE
			SYNTAX  Counter64
			MAX-ACCESS read-only
			STATUS current
			DESCRIPTION
				"Flow setup number "
			::= { hwCGNBoardScalarEntry 8 }

		-- 1.3.6.1.4.1.2011.5.25.306.1.12.1.9
		hwCGNBoardRevFlowSetupNumber OBJECT-TYPE
			SYNTAX  Counter64
			MAX-ACCESS read-only
			STATUS current
			DESCRIPTION
				"Reverse flow setup number ."
			::= { hwCGNBoardScalarEntry 9 }			

		-- 1.3.6.1.4.1.2011.5.25.306.1.12.1.10
		hwCGNBoardBandwidthNumber OBJECT-TYPE
			SYNTAX  Counter64
			MAX-ACCESS read-only
			STATUS current
			DESCRIPTION
				"Board bandwidth number,unit is G"
			::= { hwCGNBoardScalarEntry 10 }

		-- 1.3.6.1.4.1.2011.5.25.306.1.12.1.11
		hwCGNBoardDsliteTunnelNumber OBJECT-TYPE
			SYNTAX  Counter64
			MAX-ACCESS read-only
			STATUS current
			DESCRIPTION
				"Board dslite tunnel number"
			::= { hwCGNBoardScalarEntry 11 }
			
	         
																	
		-- 1.3.6.1.4.1.2011.5.25.360.1.13
		hwCGNScalar OBJECT IDENTIFIER ::= { hwCGNObjects 13 }
		
		-- 1.3.6.1.4.1.2011.5.25.360.1.11.1
		hwCGNTotalSessionNumber OBJECT-TYPE
			SYNTAX Counter64
			MAX-ACCESS read-only
			STATUS     current
			DESCRIPTION
				"Total sesssion number,uint is M"
			::= { hwCGNScalar 1 }
			
		-- 1.3.6.1.4.1.2011.5.25.360.1.11.2
		hwCGNTotalCurSessionNumber OBJECT-TYPE
			SYNTAX Counter64
			MAX-ACCESS read-only
			STATUS     current
			DESCRIPTION
				"Total current sesssion number."
			::= { hwCGNScalar 2 }			
			
		-- 1.3.6.1.4.1.2011.5.25.360.1.11.3
		hwCGNTotalPacketThroughputNumber OBJECT-TYPE
			SYNTAX Counter64
			MAX-ACCESS read-only
			STATUS     current
			DESCRIPTION
				"Total packet throughput number."
			::= { hwCGNScalar 3 }

		-- 1.3.6.1.4.1.2011.5.25.360.1.11.4
		hwCGNTotalRevPacketThroughputNumber OBJECT-TYPE
			SYNTAX Counter64
			MAX-ACCESS read-only
			STATUS     current
			DESCRIPTION
				"Total reverse packet throughput number."
			::= { hwCGNScalar 4 }

		-- 1.3.6.1.4.1.2011.5.25.360.1.11.5
		hwCGNTotalBitThroughputNumber OBJECT-TYPE
			SYNTAX Counter64
			MAX-ACCESS read-only
			STATUS     current
			DESCRIPTION
				"Total bit throughput number."
			::= { hwCGNScalar 5 }

		-- 1.3.6.1.4.1.2011.5.25.360.1.11.6
		hwCGNTotalRevBitThroughputNumber OBJECT-TYPE
			SYNTAX Counter64
			MAX-ACCESS read-only
			STATUS     current
			DESCRIPTION
				"Total reverse bit throughput number."
			::= { hwCGNScalar 6 }
			
		-- 1.3.6.1.4.1.2011.5.25.360.1.11.7
		hwCGNTotalFlowSetupNumber OBJECT-TYPE
			SYNTAX Counter64
			MAX-ACCESS read-only
			STATUS     current
			DESCRIPTION
				"Total flow setup number."
			::= { hwCGNScalar 7 }			

		-- 1.3.6.1.4.1.2011.5.25.360.1.11.8
		hwCGNTotalRevFlowSetupNumber OBJECT-TYPE
			SYNTAX Counter64
			MAX-ACCESS read-only
			STATUS     current
			DESCRIPTION
				"Total reverse flow setup number."
			::= { hwCGNScalar 8 }
									
		-- 1.3.6.1.4.1.2011.5.25.360.1.11.9
		hwCGNTotalBandwithNumber OBJECT-TYPE
			SYNTAX Counter64
			MAX-ACCESS read-only
			STATUS     current
			DESCRIPTION
				"Total bandwith number,unit is G"
			::= { hwCGNScalar 9 }

		-- 1.3.6.1.4.1.2011.5.25.360.1.11.10
		hwCGNTotalDsliteTunnelNumber OBJECT-TYPE
			SYNTAX Counter64
			MAX-ACCESS read-only
			STATUS     current
			DESCRIPTION
				"Total dslite tunnel number"
			::= { hwCGNScalar 10 }

		-- 1.3.6.1.4.1.2011.5.25.306.1.14
		hwCGNExcludeIPTable OBJECT-TYPE
			SYNTAX SEQUENCE OF HwCGNExcludeIPEntry
			MAX-ACCESS not-accessible
			STATUS current
			DESCRIPTION
				"The hwCGNSessionTable provides the configuration of address-group exclude ip information"
			::= { hwCGNObjects 14 }
			
		-- 1.3.6.1.4.1.2011.5.25.306.1.14.1
		hwCGNExcludeIPEntry OBJECT-TYPE
			SYNTAX HwCGNExcludeIPEntry
			MAX-ACCESS not-accessible
			STATUS current
			DESCRIPTION
				"Description."
			INDEX { hwCGNExcludeInstanceType,
			        hwCGNExcludeInstanceIndex,
			        hwCGNExcludeAddressIndex,
			        hwCGNExcludeSectionId,
			        hwCGNExcludeIndex}
			::= { hwCGNExcludeIPTable 1 }		
		
		HwCGNExcludeIPEntry ::=
			SEQUENCE { 
				hwCGNExcludeInstanceType
					INTEGER,
				hwCGNExcludeInstanceIndex
					Unsigned32,
				hwCGNExcludeAddressIndex
				        Unsigned32,
				hwCGNExcludeSectionId
				        Unsigned32,
				hwCGNExcludeIndex
				        Unsigned32,
				hwCGNExcludeStartIp
				        DisplayString, 
				hwCGNExcludeEndIp 
				        DisplayString            	
		}
		
		-- 1.3.6.1.4.1.2011.5.25.306.1.14.1.1
		hwCGNExcludeInstanceType OBJECT-TYPE
			SYNTAX  INTEGER
			        {
	                             nat(0),
	                             dslite(1)			        
			        } 
			MAX-ACCESS read-only
			STATUS current
			DESCRIPTION
				"Instance type."
			::= { hwCGNExcludeIPEntry 1 }

		-- 1.3.6.1.4.1.2011.5.25.306.1.14.1.2
		hwCGNExcludeInstanceIndex OBJECT-TYPE
			SYNTAX  Unsigned32(0..63)
			MAX-ACCESS read-only
			STATUS current
			DESCRIPTION
				"Instance index."
			::= { hwCGNExcludeIPEntry 2 }

		-- 1.3.6.1.4.1.2011.5.25.306.1.14.1.3
		hwCGNExcludeAddressIndex OBJECT-TYPE
			SYNTAX  Unsigned32(0..127)
			MAX-ACCESS read-only
			STATUS current
			DESCRIPTION
				"Address-group index."
			::= { hwCGNExcludeIPEntry 3 }

		-- 1.3.6.1.4.1.2011.5.25.306.1.14.1.4
		hwCGNExcludeSectionId OBJECT-TYPE
			SYNTAX  Unsigned32(0..15 | 255)
			MAX-ACCESS read-only
			STATUS current
			DESCRIPTION
				"Address-group index."
			::= { hwCGNExcludeIPEntry 4 }
			
		-- 1.3.6.1.4.1.2011.5.25.306.1.14.1.5
		hwCGNExcludeIndex OBJECT-TYPE
			SYNTAX  Unsigned32(0..9)
			MAX-ACCESS read-only
			STATUS current
			DESCRIPTION
				"Exclude rule index."
			::= { hwCGNExcludeIPEntry 5 }
			
		-- 1.3.6.1.4.1.2011.5.25.306.1.14.1.6
		hwCGNExcludeStartIp OBJECT-TYPE
			SYNTAX  DisplayString(SIZE (0..31))
			MAX-ACCESS read-only
			STATUS current
			DESCRIPTION
				"Exclude start ip address."
			::= { hwCGNExcludeIPEntry 6 }

		-- 1.3.6.1.4.1.2011.5.25.306.1.14.1.7
		hwCGNExcludeEndIp OBJECT-TYPE
			SYNTAX  DisplayString(SIZE (0..31))
			MAX-ACCESS read-only
			STATUS current
			DESCRIPTION
				"Exclude end ip address."
			::= { hwCGNExcludeIPEntry 7 } 
       									
		--modified
		-- 1.3.6.1.4.1.2011.5.25.306.1.10
		hwCGNDiscardInfoTable OBJECT-TYPE
			SYNTAX SEQUENCE OF  HwCGNDiscardInfoEntry
			MAX-ACCESS not-accessible
			STATUS current
			DESCRIPTION
				"NAT statistics information discard"
			::= { hwCGNObjects 15 }

		-- 1.3.6.1.4.1.2011.5.25.240.1.9.1
		hwCGNDiscardInfoEntry OBJECT-TYPE
			SYNTAX HwCGNDiscardInfoEntry
			MAX-ACCESS not-accessible
			STATUS current
			DESCRIPTION
				"Description."
			INDEX { hwCGNEntityPhysicalIndex,
					hwCGNDiscarInfoIndex}
			::= { hwCGNDiscardInfoTable 1 }
			
		HwCGNDiscardInfoEntry ::=
			SEQUENCE {
                        hwCGNEntityPhysicalIndex
                           Unsigned32,                                                 
                        hwCGNDiscarInfoIndex
                           Unsigned32,                                                 
                        hwCGNDiscarInfo
                           DisplayString,
                        hwCGNDiscarNumber
                           Counter64
    				 }
					 
		hwCGNEntityPhysicalIndex OBJECT-TYPE
			SYNTAX Unsigned32
			MAX-ACCESS read-only
			STATUS     current
			DESCRIPTION
				"Physical index."
			::= { hwCGNDiscardInfoEntry 1 }	
			
		hwCGNDiscarInfoIndex OBJECT-TYPE
			SYNTAX Unsigned32(0..87)
			MAX-ACCESS read-only
			STATUS     current
			DESCRIPTION
				"NAT discard information index."
			::= { hwCGNDiscardInfoEntry 2 }	
					 
		hwCGNDiscarInfo OBJECT-TYPE
			SYNTAX DisplayString (SIZE (0..255))
			MAX-ACCESS read-only
			STATUS     current
			DESCRIPTION
				"NAT discard information."
			::= { hwCGNDiscardInfoEntry 3 }	

		hwCGNDiscarNumber OBJECT-TYPE
			SYNTAX Counter64
			MAX-ACCESS read-only
			STATUS     current
			DESCRIPTION
				"NAT discard number."
			::= { hwCGNDiscardInfoEntry 4 }	
			
			
		hwCGNStatisticsPortNumDistrTable OBJECT-TYPE
			SYNTAX SEQUENCE OF  HwCGNStatisticsPortNumDistrEntry
			MAX-ACCESS not-accessible
			STATUS current
			DESCRIPTION
				"Statistic the distribution of port usage of NAT instance."
			::= { hwCGNObjects 16 }
		
		hwCGNStatisticsPortNumDistrEntry OBJECT-TYPE
			SYNTAX HwCGNStatisticsPortNumDistrEntry
			MAX-ACCESS not-accessible
			STATUS current
			DESCRIPTION
				"Description."
			INDEX { hwCGNDistrInstanceType,
					hwCGNDistrInstanceIndex}
			::= { hwCGNStatisticsPortNumDistrTable 1 } 
			
		 	HwCGNStatisticsPortNumDistrEntry ::=
			SEQUENCE {
                        hwCGNDistrInstanceType
                           INTEGER,                                                 
                        hwCGNDistrInstanceIndex
                           Unsigned32,                                                 
                        hwCGNDistrInstanceName
                           DisplayString,
                        hwCGN128PortsUserNumber
                           Unsigned32,
                        hwCGN256PortsUserNumber
                           Unsigned32,      
                        hwCGN512PortsUserNumber
                           Unsigned32,
                        hwCGN1024PortsUserNumber
                           Unsigned32,
                        hwCGN2048PortsUserNumber
                           Unsigned32,
                        hwCGN4096PortsUserNumber
                           Unsigned32, 
                        hwCGN6144PortsUserNumber
                           Unsigned32,
                        hwCGN8192PortsUserNumber
                           Unsigned32,
                        hwCGN10240PortsUserNumber
                           Unsigned32,
                        hwCGNAbovePortsUserNumber
                           Unsigned32                           
    				 } 
    				 
    	hwCGNDistrInstanceType OBJECT-TYPE
			SYNTAX  INTEGER 
					{
						nat(0)	
					}	        
			MAX-ACCESS read-only
			STATUS     current
			DESCRIPTION
				"The instance type."
			::= { hwCGNStatisticsPortNumDistrEntry 1 }
			
		hwCGNDistrInstanceIndex OBJECT-TYPE
			SYNTAX Unsigned32(0..63)
			MAX-ACCESS read-only
			STATUS     current
			DESCRIPTION
				"The instance index."
			::= { hwCGNStatisticsPortNumDistrEntry 2 }  
			
		hwCGNDistrInstanceName OBJECT-TYPE
			SYNTAX DisplayString (SIZE (1..31))
			MAX-ACCESS read-only
			STATUS     current
			DESCRIPTION
				"The instance name."
			::= { hwCGNStatisticsPortNumDistrEntry 3 }
			
		hwCGN128PortsUserNumber OBJECT-TYPE
			SYNTAX Unsigned32
			MAX-ACCESS read-only
			STATUS     current
			DESCRIPTION
				"The distribution of port usage from 0 to 127."
			::= { hwCGNStatisticsPortNumDistrEntry 4 } 
			
		hwCGN256PortsUserNumber OBJECT-TYPE
			SYNTAX Unsigned32
			MAX-ACCESS read-only
			STATUS     current
			DESCRIPTION
				"The distribution of port usage from 128 to 255."
			::= { hwCGNStatisticsPortNumDistrEntry 5 } 
			               
		hwCGN512PortsUserNumber OBJECT-TYPE
			SYNTAX Unsigned32
			MAX-ACCESS read-only
			STATUS     current
			DESCRIPTION
				"The distribution of port usage from 256 to 511."
			::= { hwCGNStatisticsPortNumDistrEntry 6 }  
			
		hwCGN1024PortsUserNumber OBJECT-TYPE
			SYNTAX Unsigned32
			MAX-ACCESS read-only
			STATUS     current
			DESCRIPTION
				"The distribution of port usage from 512 to 1023."
			::= { hwCGNStatisticsPortNumDistrEntry 7 }
			
	    hwCGN2048PortsUserNumber OBJECT-TYPE
			SYNTAX Unsigned32
			MAX-ACCESS read-only
			STATUS     current
			DESCRIPTION
				"The distribution of port usage from 1024 to 2047."
			::= { hwCGNStatisticsPortNumDistrEntry 8 }     
			
		hwCGN4096PortsUserNumber OBJECT-TYPE
			SYNTAX Unsigned32
			MAX-ACCESS read-only
			STATUS     current
			DESCRIPTION
				"The distribution of port usage from 2048 to 4095."
			::= { hwCGNStatisticsPortNumDistrEntry 9 }        
			
		hwCGN6144PortsUserNumber OBJECT-TYPE
			SYNTAX Unsigned32
			MAX-ACCESS read-only
			STATUS     current
			DESCRIPTION
				"The distribution of port usage from 4096 to 6143."
			::= { hwCGNStatisticsPortNumDistrEntry 10 }  
			
		hwCGN8192PortsUserNumber OBJECT-TYPE
			SYNTAX Unsigned32
			MAX-ACCESS read-only
			STATUS     current
			DESCRIPTION
				"The distribution of port usage from 6144 to 8191."
			::= { hwCGNStatisticsPortNumDistrEntry 11 }  
			
		hwCGN10240PortsUserNumber OBJECT-TYPE
			SYNTAX Unsigned32
			MAX-ACCESS read-only
			STATUS     current
			DESCRIPTION
				"The distribution of port usage from 8192 to 10239."
			::= { hwCGNStatisticsPortNumDistrEntry 12 }   
			
		hwCGNAbovePortsUserNumber OBJECT-TYPE
			SYNTAX Unsigned32
			MAX-ACCESS read-only
			STATUS     current
			DESCRIPTION
				"The distribution of port usage from 10240 to 65535."
			::= { hwCGNStatisticsPortNumDistrEntry 13 }
			
		-- 1.3.6.1.4.1.2011.5.25.306.1.17
		hwCGNMulBoardScalarTable OBJECT-TYPE
			SYNTAX SEQUENCE OF HwCGNMulBoardScalarEntry
			MAX-ACCESS not-accessible
			STATUS current
			DESCRIPTION
				"The hwCGNSessionTable provides the configuration of CGN bandwidth"
			::= { hwCGNObjects 17 }
			
		-- 1.3.6.1.4.1.2011.5.25.306.1.17.1
		hwCGNMulBoardScalarEntry OBJECT-TYPE
			SYNTAX HwCGNMulBoardScalarEntry
			MAX-ACCESS not-accessible
			STATUS current
			DESCRIPTION
				"Description."
			INDEX {  hwCGNMulBoardSlotIndex , hwCGNMulBoardFrameIndex }
			::= { hwCGNMulBoardScalarTable 1 }		
		
		HwCGNMulBoardScalarEntry ::=
			SEQUENCE { 
				hwCGNMulBoardSlotIndex
					Unsigned32,
				hwCGNMulBoardFrameIndex
					Unsigned32,
				hwCGNMulBoardSessionNumber
					Counter64,
				hwCGNMulBoardCurSessionNumber
				        Counter64,
				hwCGNMulBoardPacketThoughputNumber
				        Counter64,
				hwCGNMulBoardBitThoughputNumber
				        Counter64,
				hwCGNMulBoardRevPacketThoughputNumber
				        Counter64,
				hwCGNMulBoardRevBitThoughputNumber
				        Counter64,
				hwCGNMulBoardFlowSetupNumber
				        Counter64,
				hwCGNMulBoardRevFlowSetupNumber
				        Counter64,							        				
				hwCGNMulBoardBandwidthNumber
				        Counter64,
				hwCGNMulBoardDsliteTunnelNumber
				        Counter64
		}

		-- 1.3.6.1.4.1.2011.5.25.306.1.17.1.1
		hwCGNMulBoardSlotIndex OBJECT-TYPE
			SYNTAX  Unsigned32
			MAX-ACCESS read-only
			STATUS current
			DESCRIPTION
				"Slot Index."
			::= { hwCGNMulBoardScalarEntry 1 }

                                           -- 1.3.6.1.4.1.2011.5.25.306.1.17.1.2
		hwCGNMulBoardFrameIndex OBJECT-TYPE
			SYNTAX  Unsigned32
			MAX-ACCESS read-only
			STATUS current
			DESCRIPTION
				"Frame Index."
			::= { hwCGNMulBoardScalarEntry 2 }
					
		-- 1.3.6.1.4.1.2011.5.25.306.1.17.1.3
		hwCGNMulBoardSessionNumber OBJECT-TYPE
			SYNTAX  Counter64
			MAX-ACCESS read-only
			STATUS current
			DESCRIPTION
				"Board session number,unit is M"
			::= { hwCGNMulBoardScalarEntry 3 }

		-- 1.3.6.1.4.1.2011.5.25.306.1.17.1.4
		hwCGNMulBoardCurSessionNumber OBJECT-TYPE
			SYNTAX  Counter64
			MAX-ACCESS read-only
			STATUS current
			DESCRIPTION
				"Board current session number."
			::= { hwCGNMulBoardScalarEntry 4 }

		-- 1.3.6.1.4.1.2011.5.25.306.1.17.1.5
		hwCGNMulBoardPacketThoughputNumber OBJECT-TYPE
			SYNTAX  Counter64
			MAX-ACCESS read-only
			STATUS current
			DESCRIPTION
				"Board packet thoughput number."
			::= { hwCGNMulBoardScalarEntry 5 }

		-- 1.3.6.1.4.1.2011.5.25.306.1.17.1.6
		hwCGNMulBoardBitThoughputNumber OBJECT-TYPE
			SYNTAX  Counter64
			MAX-ACCESS read-only
			STATUS current
			DESCRIPTION
				"Board reverse packet thoughput number."
			::= { hwCGNMulBoardScalarEntry 6 }

		-- 1.3.6.1.4.1.2011.5.25.306.1.17.1.7
		hwCGNMulBoardRevPacketThoughputNumber OBJECT-TYPE
			SYNTAX  Counter64
			MAX-ACCESS read-only
			STATUS current
			DESCRIPTION
				"Board bit thoughput number."
			::= { hwCGNMulBoardScalarEntry 7 }
			
		-- 1.3.6.1.4.1.2011.5.25.306.1.17.1.8
		hwCGNMulBoardRevBitThoughputNumber OBJECT-TYPE
			SYNTAX  Counter64
			MAX-ACCESS read-only
			STATUS current
			DESCRIPTION
				"Board reverse bit thoughput number."
			::= { hwCGNMulBoardScalarEntry 8 }

		-- 1.3.6.1.4.1.2011.5.25.306.1.17.1.9
		hwCGNMulBoardFlowSetupNumber OBJECT-TYPE
			SYNTAX  Counter64
			MAX-ACCESS read-only
			STATUS current
			DESCRIPTION
				"Flow setup number "
			::= { hwCGNMulBoardScalarEntry 9 }

		-- 1.3.6.1.4.1.2011.5.25.306.1.17.1.10
		hwCGNMulBoardRevFlowSetupNumber OBJECT-TYPE
			SYNTAX  Counter64
			MAX-ACCESS read-only
			STATUS current
			DESCRIPTION
				"Reverse flow setup number ."
			::= { hwCGNMulBoardScalarEntry 10 }			

		-- 1.3.6.1.4.1.2011.5.25.306.1.17.1.11
		hwCGNMulBoardBandwidthNumber OBJECT-TYPE
			SYNTAX  Counter64
			MAX-ACCESS read-only
			STATUS current
			DESCRIPTION
				"Board bandwidth number,unit is G"
			::= { hwCGNMulBoardScalarEntry 11 }

		-- 1.3.6.1.4.1.2011.5.25.306.1.17.1.12
		hwCGNMulBoardDsliteTunnelNumber OBJECT-TYPE
			SYNTAX  Counter64
			MAX-ACCESS read-only
			STATUS current
			DESCRIPTION
				"Board dslite tunnel number"
			::= { hwCGNMulBoardScalarEntry 12 }
			
		--modified
															
		-- 1.3.6.1.4.1.2011.5.25.306.2
		hwCGNConformance OBJECT IDENTIFIER ::= { hwCGNMIB 2 }

		-- 1.3.6.1.4.1.2011.5.25.240.3.1
		hwCGNCompliances OBJECT IDENTIFIER ::= { hwCGNConformance 1 }

		-- 1.3.6.1.4.1.2011.5.25.306.3.1.1
		hwCGNCompliance MODULE-COMPLIANCE
			STATUS current
			DESCRIPTION 
				"Description."
			MODULE -- this module
				MANDATORY-GROUPS {hwCGNInstanceGroup,hwCGNSessionGroup,hwCGNAddressGroup,hwCGNUserPortInformationGroup,hwCGNUserSessionInformationGroup,hwCGNDsliteTunnelGroup,
				hwCGNDsliteTunnelGroup ,hwCGNTransmitAbilityGroup,hwCGNCurrentSessionGroup ,hwCGNAddressGroupInfoGroup,hwCGNBandwidthGroup,hwCGNBoardScalarGroup,hwCGNScalarGroup,
				hwCGNDiscardInfoGroup, hwCGNStatisticsPortNumDistrGroup, hwCGNMulBoardScalarTable}
			::= { hwCGNCompliances 1 }

		-- 1.3.6.1.4.1.2011.5.25.306.3.2
		hwCGNGroups OBJECT IDENTIFIER ::= { hwCGNConformance 2 }

		-- 1.3.6.1.4.1.2011.5.25.306.3.2.1
		hwCGNInstanceGroup OBJECT-GROUP
			OBJECTS {hwCGNInstanceName,hwCGNSessionLimitState,hwCGNSessionLimitICMPNumber,hwCGNSessionLimitTCPNumber,hwCGNSessionLimitUDPNumber,hwCGNSessionLimitTotalNumber,hwCGNPortRangeNumber }
			STATUS current
			DESCRIPTION 
				"Description."
			::= { hwCGNGroups 1 }

		-- 1.3.6.1.4.1.2011.5.25.306.3.2.2
		hwCGNSessionGroup OBJECT-GROUP
			OBJECTS {hwSessionEntPhysicalIndex,hwCGNSessionNumber}
			STATUS current
			DESCRIPTION 
				"Description."
			::= { hwCGNGroups 2 }  

		-- 1.3.6.1.4.1.2011.5.25.306.3.2.3
		hwCGNAddressGroup OBJECT-GROUP
			OBJECTS {hwCGNInstanceType,hwCGNInstanceIndex,hwCGNAddressGroupIndex,hwCGNAddressInstanceName,hwCGNAddressGroupName,hwCGNAddressGroupUsage}
			STATUS current
			DESCRIPTION 
				"Description."
			::= { hwCGNGroups 3 }                 

 		-- 1.3.6.1.4.1.2011.5.25.306.3.2.4
		hwCGNUserPortInformationGroup OBJECT-GROUP
			OBJECTS {hwCGNPortUserId,hwCGNUserPortICMPNumber,hwCGNUserPortTCPNumber,hwCGNUserPortUDPNumber,hwCGNUserPortTotalNumber}
			STATUS current
			DESCRIPTION 
				"Description."
			::= { hwCGNGroups 4 }                 
 
 		-- 1.3.6.1.4.1.2011.5.25.306.3.2.5
		hwCGNUserSessionInformationGroup OBJECT-GROUP
			OBJECTS {hwCGNSessionUserId,hwCGNUserSessionICMPNumber,hwCGNUserSessionTCPNumber,hwCGNUserSessionUDPNumber,hwCGNUserSessionTOTALNumber,hwCGNUserRevSessionICMPNumber,
                             hwCGNUserRevSessionTCPNumber,hwCGNUserRevSessionUDPNumber}
			STATUS current
			DESCRIPTION 
				"Description."
			::= { hwCGNGroups 5 }                 

 		-- 1.3.6.1.4.1.2011.5.25.306.3.2.6
		hwCGNDsliteTunnelGroup OBJECT-GROUP
			OBJECTS {hwTunnelEntPhysicalIndex,hwCGNCurTunnelNumber}
			STATUS current
			DESCRIPTION 
				"Description."
			::= { hwCGNGroups 6 }                 
                
 		-- 1.3.6.1.4.1.2011.5.25.306.3.2.7
		hwCGNTransmitAbilityGroup OBJECT-GROUP
			OBJECTS {hwEntPhysicalIndex,hwCGNTotalPacketForwardingThroughput,hwCGNTotalBitForwardingThroughput,
			         hwCGNTotalPacketRevForwardingThroughput,hwCGNTotalBitRevForwardingThroughput,hwCGNTotalFlowSetupRate,
			         hwCGNTotalRevFlowSetupRate}
			STATUS current
			DESCRIPTION 
				"Description."
			::= { hwCGNGroups 7 }
			
 		-- 1.3.6.1.4.1.2011.5.25.306.3.2.8
		hwCGNCurrentSessionGroup OBJECT-GROUP
			OBJECTS {hwCurSessionEntPhysicalIndex,hwCGNCurSessionNumber}
			STATUS current
			DESCRIPTION 
				"Description."
			::= { hwCGNGroups 8 }			                 
 
  		-- 1.3.6.1.4.1.2011.5.25.306.3.2.9
		hwCGNAddressGroupInfoGroup OBJECT-GROUP
			OBJECTS {hwCGNAddressInstanceType,hwCGNAddressInstanceIndex,hwCGNAddressIndex,hwCGNAddressSectionId,
			         hwCGNAddressGroupStartAddr,hwCGNAddressGroupEndAddr,hwCGNAddressGroupMaskAddr,hwCGNAddressGroupMaskNumber,
			         hwCGNAddressVPNInstanceName}
			STATUS current
			DESCRIPTION 
				"Description."
			::= { hwCGNGroups 9 }	  
			
  		-- 1.3.6.1.4.1.2011.5.25.306.3.2.10
		hwCGNStatisticsInfoGroup OBJECT-GROUP
			OBJECTS {hwCGNEntPhysicalIndex,hwCGNDiscardNumber,hwCGNErrorNumber,hwCGNServermapNumber,hwCGNFragSSNNumber,hwCGNNat444SessionNumber,
					 hwCGNDsliteSessionNumber,hwCGNReceivedPacket,hwCGNTransmittedPacket,hwCGNSessionTableNumber,hwCGNUserTableNumber,
					 --modified
					 hwCGNNat64SessionNumber,hwCGNPCPSessionNumber,hwCGNPCPNAT444SessionNumber,hwCGNPCPDSLITESessionNumber,hwCGNPCPLAFT6SessionNumber,
					 hwCGNCurrentSessionSpeed,hwCGNTotalSetupSession,hwCGNTotalTearDownSession}
					 --modified
			STATUS current
			DESCRIPTION 
				"Description."
			::= { hwCGNGroups 10 }	
			
  		-- 1.3.6.1.4.1.2011.5.25.306.3.2.11
		hwCGNBandwidthGroup OBJECT-GROUP
			OBJECTS {hwBandwidthEntPhysicalIndex,hwCGNBandwidthNumber}
			STATUS current
			DESCRIPTION 
				"Description."
			::= { hwCGNGroups 11 }
				
		-- 1.3.6.1.4.1.2011.5.25.306.3.2.12	
		hwCGNBoardScalarGroup OBJECT-GROUP
			OBJECTS {hwCGNBoardSlotIndex,hwCGNBoardSessionNumber,hwCGNBoardCurSessionNumber,
			         hwCGNBoardPacketThoughputNumber,hwCGNBoardBitThoughputNumber,hwCGNBoardRevPacketThoughputNumber,
			         hwCGNBoardRevBitThoughputNumber,hwCGNBoardFlowSetupNumber,hwCGNBoardRevFlowSetupNumber,
			         hwCGNBoardBandwidthNumber}
			STATUS current
			DESCRIPTION 
				"Description."
			::= { hwCGNGroups 12 }	

		-- 1.3.6.1.4.1.2011.5.25.306.3.2.13	
		hwCGNScalarGroup OBJECT-GROUP
			OBJECTS {hwCGNTotalSessionNumber,hwCGNTotalCurSessionNumber,hwCGNTotalPacketThroughputNumber,hwCGNTotalRevPacketThroughputNumber,hwCGNTotalBitThroughputNumber,hwCGNTotalRevBitThroughputNumber,hwCGNTotalFlowSetupNumber,hwCGNTotalRevFlowSetupNumber,hwCGNTotalBandwithNumber,hwCGNTotalDsliteTunnelNumber}
			STATUS current
			DESCRIPTION 
				"Description."
			::= { hwCGNGroups 13 }

		-- 1.3.6.1.4.1.2011.5.25.306.3.2.14	
		hwCGNExcludeIPGroup OBJECT-GROUP
			OBJECTS {hwCGNExcludeInstanceType,hwCGNExcludeInstanceIndex,hwCGNExcludeAddressIndex,hwCGNExcludeSectionId,hwCGNExcludeIndex,hwCGNExcludeStartIp,hwCGNExcludeEndIp}
			STATUS current
			DESCRIPTION 
				"Description."
			::= { hwCGNGroups 14 } 
			
		-- 1.3.6.1.4.1.2011.5.25.306.3.2.15	
		hwCGNDiscardInfoGroup OBJECT-GROUP  
			OBJECTS {hwCGNEntityPhysicalIndex,hwCGNDiscarInfoIndex,hwCGNDiscarInfo,hwCGNDiscarNumber}
			STATUS current
			DESCRIPTION 
				"Description."
			::= { hwCGNGroups 15 }       
			
		-- 1.3.6.1.4.1.2011.5.25.306.3.2.16	
		hwCGNStatisticsPortNumDistrGroup OBJECT-GROUP  
			OBJECTS {hwCGNDistrInstanceType, hwCGNDistrInstanceIndex, hwCGNDistrInstanceName, hwCGN128PortsUserNumber,
                     hwCGN256PortsUserNumber, hwCGN512PortsUserNumber, hwCGN1024PortsUserNumber, hwCGN2048PortsUserNumber,
                     hwCGN4096PortsUserNumber, hwCGN6144PortsUserNumber, hwCGN8192PortsUserNumber, hwCGN10240PortsUserNumber,
                     hwCGNAbovePortsUserNumber}
			STATUS current
			DESCRIPTION 
				"Description."
			::= { hwCGNGroups 16 }  
			
		-- 1.3.6.1.4.1.2011.5.25.306.3.2.17	
		hwCGNMulBoardScalarGroup OBJECT-GROUP
			OBJECTS {hwCGNMulBoardSlotIndex,hwCGNMulBoardFrameIndex,hwCGNMulBoardSessionNumber,hwCGNMulBoardCurSessionNumber,
			         hwCGNMulBoardPacketThoughputNumber,hwCGNMulBoardBitThoughputNumber,hwCGNMulBoardRevPacketThoughputNumber,
			         hwCGNMulBoardRevBitThoughputNumber,hwCGNMulBoardFlowSetupNumber,hwCGNMulBoardRevFlowSetupNumber,
			         hwCGNMulBoardBandwidthNumber}
			STATUS current
			DESCRIPTION 
				"Description."
			::= { hwCGNGroups 17 }						
				       														         
	END

--
-- HUAWEI-CGN-MIB.mib
--
