-- Copyright (C) 2015 by HUAWEI TECHNOLOGIES. All rights reserved.
--
-- HUAWEI-NETCONF-MIB.mib
-- MIB generated by MG-SOFT Visual MIB Builder Version 4.0 Build 341
-- Wednesday, April 21, 2010 at 16:16:33
-- Version: V2.03
--

	HUAWEI-NETCONF-MIB DEFINITIONS ::= BEGIN
 
		IMPORTS
			hwDatacomm			
				FROM HUAWEI-MIB	
			InetAddressType, InetAddress
				FROM INET-ADDRESS-MIB				
			OBJECT-GROUP, MODULE-COMPLIANCE, NOTIFICATION-GROUP			
				FROM SNMPv2-CONF			
			IpAddress, OBJECT-TYPE, MODULE-IDENTITY, NOTIFICATION-TYPE			
				FROM SNMPv2-SMI;
	
	
		-- 1.3.6.1.4.1.2011.5.25.217
		hwNetconf MODULE-IDENTITY 
			LAST-UPDATED "201511271225Z"		-- November 27, 2015 at 16:19 GMT
			ORGANIZATION 
				"Huawei Technologies Co.,Ltd."
			CONTACT-INFO 
				"Huawei Industrial Base
				  Bantian, Longgang
				   Shenzhen 518129
                                   People's Republic of China
                                   Website: http://www.huawei.com
                                   Email: support@huawei.com
                                 "
			DESCRIPTION 
				"This defines the MIB for the Netconf Agent"

	                                 REVISION     "201511271225Z"
                            DESCRIPTION  "V2.0.3, add hwNetconfServerSyncConfigFail."

                                                       REVISION     "201506081225Z"
                            DESCRIPTION  "V2.0.2, modify hwNetconfSessionPeerIPAddress hwNetconfSessionVpnName OID"
							
		            REVISION     "201505151225Z"
                            DESCRIPTION  "V2.0.1, add hwNetconfClientConnectionInterrupt, hwNetconfClientConnectionResume, hwNetconfServerConnectionInterrupt, hwNetconfServerConnectionResume."	
                        
			    REVISION     "201004080000Z"
                            DESCRIPTION  
                            "
                            V1.00, Inital version.
                            "     
                            
			::= { hwDatacomm 217 }

		
	
--
-- Node definitions
--
	
		-- 1.3.6.1.4.1.2011.5.25.217.1
		hwNetconfAgent OBJECT IDENTIFIER ::= { hwNetconf 1 }

		
		-- 1.3.6.1.4.1.2011.5.25.217.1.1
		hwNetconfSyncFullFtpFilename OBJECT-TYPE
			SYNTAX OCTET STRING (SIZE (1..128))
			MAX-ACCESS accessible-for-notify
			STATUS current
			DESCRIPTION
				"Sync Full file being transferred using FTP."
			::= { hwNetconfAgent 1 }

		
		-- 1.3.6.1.4.1.2011.5.25.217.1.2
		hwNetconfSyncFullFtpServerAddr OBJECT-TYPE
			SYNTAX IpAddress
			MAX-ACCESS accessible-for-notify
			STATUS current
			DESCRIPTION
				"IP address of the Sync Full file transfer target FTP Server"
			::= { hwNetconfAgent 2 }

		
		-- 1.3.6.1.4.1.2011.5.25.217.1.3
		hwNetconfSyncFullFtpFailReason OBJECT-TYPE
			SYNTAX INTEGER
				{
				fileOpenError(1),
				fileTransferFailed(2)
				}
			MAX-ACCESS accessible-for-notify
			STATUS current
			DESCRIPTION
				"Reason code of the Sync Full FTP file transfer failure"
			::= { hwNetconfAgent 3 }
			
		-- 1.3.6.1.4.1.2011.5.25.217.1.4
		hwNetconfSessionInetAddrType OBJECT-TYPE
			SYNTAX InetAddressType
	        	MAX-ACCESS read-create
	        	STATUS current
	        	DESCRIPTION
	            		"This object indicates the IP address type."
	        	::= { hwNetconfAgent 4 }
			
	   	 -- 1.3.6.1.4.1.2011.5.25.217.1.5
		hwNetconfSessionPeerIPAddress OBJECT-TYPE
	        	SYNTAX IpAddress
	        	MAX-ACCESS accessible-for-notify
	        	STATUS current
	        	DESCRIPTION
	            		"Peer IP address."
	        	::= { hwNetconfAgent 5 }
		
		-- 1.3.6.1.4.1.2011.5.25.217.1.6	
		hwNetconfSessionVpnName OBJECT-TYPE
			SYNTAX OCTET STRING (SIZE (1..31))
			MAX-ACCESS accessible-for-notify
			STATUS current
			DESCRIPTION
				"The name of VPN interface."
			::= { hwNetconfAgent 6 }

		-- 1.3.6.1.4.1.2011.5.25.217.1.7
		hwNetconfSyncConfigIPAddress OBJECT-TYPE
	                     SYNTAX InetAddress
	                     MAX-ACCESS accessible-for-notify
	                     STATUS current
	                     DESCRIPTION
	                                         "IP address of the source initiating sync-config operation."
	                    ::= { hwNetconfAgent 7 }
		
		-- 1.3.6.1.4.1.2011.5.25.217.2
		hwNetconfNotifications OBJECT IDENTIFIER ::= { hwNetconf 2 }

		
		-- 1.3.6.1.4.1.2011.5.25.217.2.1
		hwNetconfSyncFullFtpFailed NOTIFICATION-TYPE
			OBJECTS { hwNetconfSyncFullFtpFilename, hwNetconfSyncFullFtpServerAddr, hwNetconfSyncFullFtpFailReason }
			STATUS current
			DESCRIPTION 
				"This notification is sent when the FTP transfer of the sync full operation file to the remote FTP Server failed."
			::= { hwNetconfNotifications 1 }
			
                hwNetconfClientConnectionInterrupt NOTIFICATION-TYPE
	                OBJECTS { hwNetconfSessionInetAddrType, hwNetconfSessionPeerIPAddress, hwNetconfSessionVpnName }
	                STATUS current
	                DESCRIPTION 
	                    "Remote netconf connection is interrupted."
	                ::=  {hwNetconfNotifications 2}
	        
	        hwNetconfClientConnectionResume NOTIFICATION-TYPE
	                OBJECTS { hwNetconfSessionInetAddrType, hwNetconfSessionPeerIPAddress, hwNetconfSessionVpnName }
	                STATUS current
	                DESCRIPTION 
	                    "Remote netconf connection is resumed."
	                ::=  {hwNetconfNotifications 3}
					
		hwNetconfServerConnectionInterrupt NOTIFICATION-TYPE
	                OBJECTS { hwNetconfSessionInetAddrType, hwNetconfSessionPeerIPAddress, hwNetconfSessionVpnName }
	                STATUS current
	                DESCRIPTION 
	                    "The connection is interrupted."
	                ::=  {hwNetconfNotifications 4}
	        
	        hwNetconfServerConnectionResume NOTIFICATION-TYPE
	                OBJECTS { hwNetconfSessionInetAddrType, hwNetconfSessionPeerIPAddress, hwNetconfSessionVpnName }
	                STATUS current
	                DESCRIPTION 
	                    "The connection is resumed."
	                ::=  {hwNetconfNotifications 5}

                             hwNetconfServerSyncConfigFail NOTIFICATION-TYPE
                                     OBJECTS { hwNetconfSessionInetAddrType, hwNetconfSyncConfigIPAddress, hwNetconfSessionVpnName }
	                STATUS current
                                     DESCRIPTION 
	                    "This notification is sent when application virtual access configurations synchronization is failed."
                                     ::= { hwNetconfNotifications 6 }
		
		-- 1.3.6.1.4.1.2011.5.25.217.3
		hwNetconfMIBConformance OBJECT IDENTIFIER ::= { hwNetconf 3 }

		
		-- 1.3.6.1.4.1.2011.5.25.217.3.1
		hwNetconfMIBCompliances OBJECT IDENTIFIER ::= { hwNetconfMIBConformance 1 }

		
		-- 1.3.6.1.4.1.2011.5.25.217.3.1.1
		hwNetconfMIBCompliance MODULE-COMPLIANCE
			STATUS current
			DESCRIPTION 
				"The compliance statement for systems supporting the HUAWEI-NETCONF-MIB."
			MODULE -- this module
				MANDATORY-GROUPS { hwNetconfNotificationGroup, hwNetconfAgentGroup, hwNetconfClientGroup }
			::= { hwNetconfMIBCompliances 1 }

		
		-- 1.3.6.1.4.1.2011.5.25.217.3.2
		hwNetconfMIBGroups OBJECT IDENTIFIER ::= { hwNetconfMIBConformance 2 }

		
		-- 1.3.6.1.4.1.2011.5.25.217.3.2.1
		hwNetconfNotificationGroup NOTIFICATION-GROUP
			NOTIFICATIONS { hwNetconfSyncFullFtpFailed, hwNetconfClientConnectionInterrupt, hwNetconfClientConnectionResume, hwNetconfServerConnectionInterrupt, hwNetconfServerConnectionResume, hwNetconfServerSyncConfigFail}
			STATUS current
			DESCRIPTION 
				"The NETCONF notification group"
			::= { hwNetconfMIBGroups 1 }

		
		-- 1.3.6.1.4.1.2011.5.25.217.3.2.2
		hwNetconfAgentGroup OBJECT-GROUP
			OBJECTS { hwNetconfSyncFullFtpFilename, hwNetconfSyncFullFtpServerAddr, hwNetconfSyncFullFtpFailReason, hwNetconfSyncConfigIPAddress }
			STATUS current
			DESCRIPTION 
				"Description."
			::= { hwNetconfMIBGroups 2 }

		-- 1.3.6.1.4.1.2011.5.25.217.4.2.3
		hwNetconfClientGroup OBJECT-GROUP
			OBJECTS { hwNetconfSessionInetAddrType, hwNetconfSessionPeerIPAddress, hwNetconfSessionVpnName }
			STATUS current
			DESCRIPTION 
				"Description."
			::= { hwNetconfMIBGroups 3 }
	
	END

--
-- HUAWEI-NETCONF-MIB.mib
--
