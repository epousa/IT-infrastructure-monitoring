-- ===================================================================
-- Copyright (C) 2016 by HUAWEI TECHNOLOGIES. All rights reserved.
-- Description: This MIB contains private managed object and notification 
--              trap definitions for virtual access.
-- Reference:
-- Version: V1.05
-- ===================================================================


    HUAWEI-VIRTUALACCESS-MIB DEFINITIONS ::= BEGIN
 
        IMPORTS
            hwDatacomm            
                FROM HUAWEI-MIB            
            ifIndex, ifName, InterfaceIndex           
                FROM IF-MIB 
            SnmpAdminString            
                FROM SNMP-FRAMEWORK-MIB       
            MODULE-COMPLIANCE, OBJECT-GROUP, NOTIFICATION-GROUP            
                FROM SNMPv2-CONF            
            Integer32, Unsigned32, Counter32, IpAddress, BITS, OBJECT-TYPE, 
            MODULE-IDENTITY, NOTIFICATION-TYPE            
                FROM SNMPv2-SMI
            InetAddressType, InetAddress
                FROM INET-ADDRESS-MIB;
    
    
        hwVirtualAccessMib MODULE-IDENTITY 
            LAST-UPDATED "201608031926Z"
            ORGANIZATION 
                "Huawei Technologies Co.,Ltd."
            CONTACT-INFO 
                "Huawei Industrial Base
                 Bantian, Longgang
                 Shenzhen 518129
                 People's Republic of China 
                 Website: http://www.huawei.com
                 Email: support@huawei.com"
            DESCRIPTION 
        "This MIB contains private managed object and notification trap definitions for virtual access."
--
-- Revision history
--    
        REVISION   "201608031926Z"
        DESCRIPTION "V1.05,Add hwVirtualAccessTunnelName hwVirtualAccessExplicitPathName  for hwVirtualAccessTunnelReOpt."

        REVISION   "201607291537Z"
        DESCRIPTION "V1.04,Add hwVirtualAccessTunnelName hwVirtualAccessExplicitPathName for hwVirtualAccessTunnelEntry."

        REVISION   "201606021422Z"
        DESCRIPTION "V1.03,Add a reason for hwVirtualAccessTunnelSwitchReason."

        REVISION   "201602291655Z"
        DESCRIPTION "V1.02,Add hwVirtualAccessTunnelHSBSwitch,hwVirtualAccessTunnelHSBResume,hwVirtualAccessTunnelHSBResume."

        REVISION   "201509101144Z"
        DESCRIPTION "V1.01, Modify Index number."

        REVISION    "201505191549Z"   
        DESCRIPTION "V1.00, initial version."
		
            ::= { hwDatacomm 343 }
    
--
-- Node definitions
--
    
        hwVirtualAccessInfo OBJECT IDENTIFIER ::= { hwVirtualAccessMib 1 }
        
        hwVirtualAccessTableInfo OBJECT IDENTIFIER ::= { hwVirtualAccessInfo 1 }
        
        hwVirtualAccessLspTable OBJECT-TYPE
            SYNTAX SEQUENCE OF HwVirtualAccessLspEntry
            MAX-ACCESS not-accessible
            STATUS current
            DESCRIPTION
                "Basic information about virtual access Lsp.
                 The index of this table is hwVirtualAccessLspSourceNodeId, hwVirtualAccessLspDestNodeId, hwVirtualAccessTunnelIdentity, hwVirtualAccessLspType.
                "
            ::= { hwVirtualAccessTableInfo 1 }
            
        hwVirtualAccessLspEntry OBJECT-TYPE
            SYNTAX HwVirtualAccessLspEntry
            MAX-ACCESS not-accessible
            STATUS current
            DESCRIPTION
                "Basic information about virtual access Lsp.
                 The index of this entry is hwVirtualAccessLspSourceNodeId, hwVirtualAccessLspDestNodeId, hwVirtualAccessTunnelIdentity, hwVirtualAccessLspType.
                "
            INDEX { hwVirtualAccessLspSourceNodeId, hwVirtualAccessLspDestNodeId, hwVirtualAccessTunnelIdentity, hwVirtualAccessLspType }
            ::= { hwVirtualAccessLspTable 1 }
            
        HwVirtualAccessLspEntry ::=
            SEQUENCE { 
                hwVirtualAccessLspSourceNodeId 
                    IpAddress,
                hwVirtualAccessLspDestNodeId 
                    IpAddress,
                hwVirtualAccessTunnelIdentity
                    Integer32,
                hwVirtualAccessLspType
                    INTEGER,
                hwVirtualAccessLspApId
                    IpAddress,
                hwVirtualAccessLspIfIndex
                    InterfaceIndex,
                hwVirtualAccessLspIfName
                    SnmpAdminString,
                hwVirtualAccessLspOperState
                    INTEGER,
                hwVirtualAccessLspId
                    Integer32                   
             }
             
        hwVirtualAccessLspSourceNodeId  OBJECT-TYPE
            SYNTAX IpAddress
            MAX-ACCESS not-accessible
            STATUS current
            DESCRIPTION
                "Indicates the administrative IP address of source node."
            ::= { hwVirtualAccessLspEntry 1 }
            
        hwVirtualAccessLspDestNodeId  OBJECT-TYPE
            SYNTAX IpAddress
            MAX-ACCESS not-accessible
            STATUS current
            DESCRIPTION
                "Indicates the administrative IP address of destination node."
            ::= { hwVirtualAccessLspEntry 2 }
            
        hwVirtualAccessTunnelIdentity OBJECT-TYPE
            SYNTAX Integer32(1..65535)
            MAX-ACCESS not-accessible
            STATUS current
            DESCRIPTION
                "Indicates the Tunnel ID."
            ::= { hwVirtualAccessLspEntry 3 }
            
        hwVirtualAccessLspType OBJECT-TYPE
			      SYNTAX INTEGER
            {
                primary(1),
                hotstandby(2)
            }
            MAX-ACCESS read-only
            STATUS current
            DESCRIPTION
                "Indicates type of VP.
                Options:
                1. primary(1)          -indicates VP type is primary.
                2. hotstandby(2)       -indicates VP type is hotstandby."
            ::= { hwVirtualAccessLspEntry 4 }
            
        hwVirtualAccessLspApId OBJECT-TYPE
            SYNTAX IpAddress
            MAX-ACCESS read-only
            STATUS current
            DESCRIPTION
                "Indicates the AP ID of failure AP."
            ::= { hwVirtualAccessLspEntry 5 }
            
        hwVirtualAccessLspIfIndex OBJECT-TYPE
            SYNTAX InterfaceIndex
            MAX-ACCESS read-only
            STATUS current
            DESCRIPTION
                "Indicates the index of failure AP interface."
            ::= { hwVirtualAccessLspEntry 6 }
            
        hwVirtualAccessLspIfName OBJECT-TYPE
            SYNTAX SnmpAdminString
            MAX-ACCESS read-only
            STATUS current
            DESCRIPTION
                "Indicates the name of failure AP interface."
            ::= { hwVirtualAccessLspEntry 7 } 
            
        hwVirtualAccessLspOperState OBJECT-TYPE
            SYNTAX INTEGER
            {
                up(1),
                down(2)
            }
            MAX-ACCESS read-only
            STATUS current
            DESCRIPTION
                "Indicates VP operate state.
                Options:
                1. up(1)          -indicates VP operate state is up.
                2. down(2)        -indicates VP operate state is down."
            ::= { hwVirtualAccessLspEntry 8 }                    
	        
        hwVirtualAccessLspId OBJECT-TYPE
            SYNTAX Integer32(1..65535)
            MAX-ACCESS read-only
            STATUS current
            DESCRIPTION
                "Indicates the VP ID."
            ::= { hwVirtualAccessLspEntry 9 }
               
        hwVirtualAccessTunnelTable OBJECT-TYPE
            SYNTAX SEQUENCE OF HwVirtualAccessTunnelEntry
            MAX-ACCESS not-accessible
            STATUS current
            DESCRIPTION
                "Basic information about virtual access Tunnel.
                 The index of this table is hwVirtualAccessTunnelSourceNodeId, hwVirtualAccessTunnelDestNodeId, hwVirtualAccessTunnelId.
                "
            ::= { hwVirtualAccessTableInfo 2 }
            
        hwVirtualAccessTunnelEntry OBJECT-TYPE
            SYNTAX HwVirtualAccessTunnelEntry
            MAX-ACCESS not-accessible
            STATUS current
            DESCRIPTION
                "Basic information about virtual access VP group.
                 The index of this entry is hwVirtualAccessTunnelSourceNodeId, hwVirtualAccessTunnelDestNodeId, hwVirtualAccessTunnelId.
                "
            INDEX { hwVirtualAccessTunnelSourceNodeId, hwVirtualAccessTunnelDestNodeId, hwVirtualAccessTunnelId }
            ::= { hwVirtualAccessTunnelTable 1 }
            
        HwVirtualAccessTunnelEntry ::=
            SEQUENCE { 
                hwVirtualAccessTunnelSourceNodeId 
                    IpAddress,
                hwVirtualAccessTunnelDestNodeId 
                    IpAddress,
                hwVirtualAccessTunnelId
                    Integer32,
                hwVirtualAccessTunnelApAdminIp
                    IpAddress,	
                hwVirtualAccessIfIndex
                    InterfaceIndex,                    
                hwVirtualAccessTunnelOperState
                    INTEGER,
                hwVirtualAccessTunnelReason
                    Integer32,
                hwVirtualAccessTunnelName
                    SnmpAdminString,
                hwVirtualAccessExplicitPathName
                    SnmpAdminString					
             }
             
        hwVirtualAccessTunnelSourceNodeId  OBJECT-TYPE
            SYNTAX IpAddress
            MAX-ACCESS read-only
            STATUS current
            DESCRIPTION
                "Indicates the source node administrative IP address of VP group."
            ::= { hwVirtualAccessTunnelEntry 1 }
            
        hwVirtualAccessTunnelDestNodeId  OBJECT-TYPE
            SYNTAX IpAddress
            MAX-ACCESS read-only
            STATUS current
            DESCRIPTION
                "Indicates the destination node administrative IP address of VP group."
            ::= { hwVirtualAccessTunnelEntry 2 }   
            
        hwVirtualAccessTunnelId OBJECT-TYPE
            SYNTAX Integer32(1..65535)
            MAX-ACCESS read-only
            STATUS current
            DESCRIPTION
                "Indicates the group ID of VP group."
            ::= { hwVirtualAccessTunnelEntry 3 } 
            
        hwVirtualAccessTunnelApAdminIp OBJECT-TYPE
            SYNTAX IpAddress
            MAX-ACCESS read-only
            STATUS current
            DESCRIPTION
                "Indicates  the last down VP ID for hwVirtualAccessTunnelDown, or the frist up VP ID for hwVirtualAccessTunnelDownClear."
            ::= { hwVirtualAccessTunnelEntry 4 }  
            
        hwVirtualAccessIfIndex OBJECT-TYPE
            SYNTAX InterfaceIndex
            MAX-ACCESS read-only
            STATUS current
            DESCRIPTION
                "Indicates the index of failure AP interface."
            ::= { hwVirtualAccessTunnelEntry 5 }
			
			
        hwVirtualAccessTunnelOperState OBJECT-TYPE
            SYNTAX INTEGER
            {
                up(1),
                down(2)
            }
            MAX-ACCESS read-only
            STATUS current
            DESCRIPTION
                "Indicates VP group operate state.
                Options:
                1. up(1)          -indicates VP group operate state is up.
                2. down(2)        -indicates VP group operate state is down."
            ::= { hwVirtualAccessTunnelEntry 6 } 
	    
	hwVirtualAccessTunnelReason OBJECT-TYPE
            SYNTAX Integer32
            MAX-ACCESS read-only
            STATUS current
            DESCRIPTION
                 "This object indicates the cause that the VP group becomes down.
                 Options:
                 1. TunnelUp(1)            --indicates Tunnel was up.
                 2. TunnelDelete(2)        --indicates Tunnel was deleted.
                 3. BfdDown(3)         --indicates BFD was down.
                 4. ApDown(4)          --indicates AP down.
                 5. ApInterfaceDown(5) --indicates AP interface was down.
                 6. other(6)           --indicates other reason.
				 "
            ::= { hwVirtualAccessTunnelEntry 7 }  
			
            hwVirtualAccessTunnelName OBJECT-TYPE
            SYNTAX SnmpAdminString
            MAX-ACCESS read-only
            STATUS current
            DESCRIPTION
                 "This object indicates name of the virtual access tunnel."
            ::= { hwVirtualAccessTunnelEntry 8 }
			
            hwVirtualAccessExplicitPathName OBJECT-TYPE
            SYNTAX SnmpAdminString
            MAX-ACCESS read-only
            STATUS current
            DESCRIPTION
                 "This object indicates the explicit path name that the tunnel binded."
            ::= { hwVirtualAccessTunnelEntry 9 }

        hwVirtualAccessLinkDownTable OBJECT-TYPE
            SYNTAX SEQUENCE OF HwVirtualAccessLinkDownEntry
            MAX-ACCESS not-accessible
            STATUS current
            DESCRIPTION
                "Basic information about virtual access link down.
                 The index of this table is hwVirtualAccessLinkDownApId, hwVirtualAccessLinkDownIfIndex.
                "
            ::= { hwVirtualAccessTableInfo 3 }
            
        hwVirtualAccessLinkDownEntry OBJECT-TYPE
            SYNTAX HwVirtualAccessLinkDownEntry
            MAX-ACCESS not-accessible
            STATUS current
            DESCRIPTION
                "Basic information about virtual access link down.
                 The index of this entry is hwVirtualAccessLinkDownApId, hwVirtualAccessLinkDownIfIndex.
                "
            INDEX { hwVirtualAccessLinkDownApId, hwVirtualAccessLinkDownIfIndex }
            ::= { hwVirtualAccessLinkDownTable 1 }
            
        HwVirtualAccessLinkDownEntry ::=
            SEQUENCE { 
                hwVirtualAccessLinkDownApId
                    IpAddress,
                hwVirtualAccessLinkDownIfIndex
                    Integer32,
                hwVirtualAccessLinkDownIfAdminStatus
                    INTEGER,
                hwVirtualAccessLinkDownIfOperStatus
                    INTEGER,
                hwVirtualAccessLinkDownIfName
                    SnmpAdminString,
               hwVirtualAccessLinkDownReason
                    Integer32
             }
             
        hwVirtualAccessLinkDownApId OBJECT-TYPE
            SYNTAX IpAddress
            MAX-ACCESS not-accessible
            STATUS current
            DESCRIPTION
                "Indicates the AP administrative IP address of failure node."
            ::= { hwVirtualAccessLinkDownEntry 1 }
            
        hwVirtualAccessLinkDownIfIndex OBJECT-TYPE
            SYNTAX Integer32(1..65535)
            MAX-ACCESS not-accessible
            STATUS current
            DESCRIPTION
                "Indicates the index of failure interface."
            ::= { hwVirtualAccessLinkDownEntry 2 }
            
        hwVirtualAccessLinkDownIfAdminStatus OBJECT-TYPE
            SYNTAX INTEGER
            {
                up(1),
                down(2)
            }
            MAX-ACCESS read-only
            STATUS current
            DESCRIPTION
                "Indicates the interface administrative operate state.
                Options:
                1. up(1)          -indicates interface administrative state is up.
                2. down(2)        -indicates interface administrative state is down."
            ::= { hwVirtualAccessLinkDownEntry 3 }       
            
        hwVirtualAccessLinkDownIfOperStatus OBJECT-TYPE
            SYNTAX INTEGER
            {
                up(1),
                down(2)
            }
            MAX-ACCESS read-only
            STATUS current
            DESCRIPTION
                "Indicates link operate state.
                Options:
                1. up(1)          -indicates link operate state is up.
                2. down(2)        -indicates link operate state is down."
            ::= { hwVirtualAccessLinkDownEntry 4 }
        
        hwVirtualAccessLinkDownIfName OBJECT-TYPE
            SYNTAX SnmpAdminString
            MAX-ACCESS read-only
            STATUS current
            DESCRIPTION
                "Indicates the name of failure interface."
            ::= { hwVirtualAccessLinkDownEntry 5 }
			
        hwVirtualAccessLinkDownReason OBJECT-TYPE
            SYNTAX Integer32(1..65535)
            MAX-ACCESS read-only
            STATUS current
            DESCRIPTION
                 "This object indicates the cause that the Link becomes down.
                 Options:
                 1. ifPhysicalLinkDown(1)     --indicates interface physical link was down.
                 2. interfaceDelete(2)        --indicates interface was deleted.
                 3. ifPhysicalLinkUp(3)       --indicates interface physical link was up.
				 "
            ::= { hwVirtualAccessLinkDownEntry 6 }
        hwVirtualAccessApSelectedMasterTable OBJECT-TYPE
            SYNTAX SEQUENCE OF HwVirtualAccessApSelectedMasterEntry
            MAX-ACCESS not-accessible
            STATUS current
            DESCRIPTION
                "Basic information about virtual access AP Selected Master.
                 The index of this table is hwVirtualAccessApIpAddress, hwVirtualAccessPrimaryMasterIpAddress, hwVirtualAccessSecondaryMasterIpAddress.
                "
            ::= { hwVirtualAccessTableInfo 4 }
        hwVirtualAccessApSelectedMasterEntry OBJECT-TYPE
            SYNTAX HwVirtualAccessApSelectedMasterEntry
            MAX-ACCESS not-accessible
            STATUS current
            DESCRIPTION
                "Basic information about virtual access AP.
                 The index of this entry is hwVirtualAccessApIpAddress, hwVirtualAccessPrimaryMasterIpAddress, hwVirtualAccessSecondaryMasterIpAddress.
                "
            INDEX { hwVirtualAccessApIpAddress, hwVirtualAccessPrimaryMasterIpAddress, hwVirtualAccessSecondaryMasterIpAddress }
            ::= { hwVirtualAccessApSelectedMasterTable 1 }
        HwVirtualAccessApSelectedMasterEntry ::=
            SEQUENCE { 
                hwVirtualAccessApIpAddress
                    IpAddress,
                hwVirtualAccessPrimaryMasterIpAddress
                    IpAddress,  
                hwVirtualAccessSecondaryMasterIpAddress
                    IpAddress
             }
             
        hwVirtualAccessApIpAddress OBJECT-TYPE
            SYNTAX IpAddress
            MAX-ACCESS read-only
            STATUS current
            DESCRIPTION
                "Indicates the AP ID of failure AP."
            ::= { hwVirtualAccessApSelectedMasterEntry 1 }
        hwVirtualAccessPrimaryMasterIpAddress OBJECT-TYPE
            SYNTAX IpAddress
            MAX-ACCESS read-only
            STATUS current
            DESCRIPTION
                "Indicates the primary master ID of failure AP."
            ::= { hwVirtualAccessApSelectedMasterEntry 2 }    
        hwVirtualAccessSecondaryMasterIpAddress OBJECT-TYPE
            SYNTAX IpAddress
            MAX-ACCESS read-only
            STATUS current
            DESCRIPTION
                "Indicates the Secondary master ID of failure AP."
            ::= { hwVirtualAccessApSelectedMasterEntry 3 }     
        hwVirtualAccessExterLinkDownTable OBJECT-TYPE
            SYNTAX SEQUENCE OF HwVirtualAccessExterLinkDownEntry
            MAX-ACCESS not-accessible
            STATUS current
            DESCRIPTION
                "Basic information about virtual access Exter link down.
                 The index of this table is hwVirtualAccessExterLinkDownApId, hwVirtualAccessExterLinkDownIfIndex.
                "
            ::= { hwVirtualAccessTableInfo 5 }
            
        hwVirtualAccessExterLinkDownEntry OBJECT-TYPE
            SYNTAX HwVirtualAccessExterLinkDownEntry
            MAX-ACCESS not-accessible
            STATUS current
            DESCRIPTION
                "Basic information about virtual access Exter link down.
                 The index of this entry is hwVirtualAccessExterLinkDownApId, hwVirtualAccessLinkDownIfIndex.
                "
            INDEX { hwVirtualAccessExterLinkDownApId, hwVirtualAccessLinkDownIfIndex }
            ::= { hwVirtualAccessExterLinkDownTable 1 }
            
        HwVirtualAccessExterLinkDownEntry ::=
            SEQUENCE { 
                hwVirtualAccessExterLinkDownApId
                    IpAddress,
                hwVirtualAccessExterLinkDownIfIndex
                    Integer32,
                hwVirtualAccessExterLinkDownIfAdminStatus
                    INTEGER,
                hwVirtualAccessExterLinkDownIfOperStatus
                    INTEGER,
                hwVirtualAccessExterLinkDownIfName
                    SnmpAdminString,
               hwVirtualAccessExterLinkDownReason
                    Integer32
             }
             
        hwVirtualAccessExterLinkDownApId OBJECT-TYPE
            SYNTAX IpAddress
            MAX-ACCESS not-accessible
            STATUS current
            DESCRIPTION
                "Indicates the AP administrative IP address of failure node."
            ::= { hwVirtualAccessExterLinkDownEntry 1 }
            
        hwVirtualAccessExterLinkDownIfIndex OBJECT-TYPE
            SYNTAX Integer32(1..65535)
            MAX-ACCESS not-accessible
            STATUS current
            DESCRIPTION
                "Indicates the index of failure interface."
            ::= { hwVirtualAccessExterLinkDownEntry 2 }
            
        hwVirtualAccessExterLinkDownIfAdminStatus OBJECT-TYPE
            SYNTAX INTEGER
            {
                up(1),
                down(2)
            }
            MAX-ACCESS read-only
            STATUS current
            DESCRIPTION
                "Indicates the interface administrative operate state.
                Options:
                1. up(1)          -indicates interface administrative state is up.
                2. down(2)        -indicates interface administrative state is down."
            ::= { hwVirtualAccessExterLinkDownEntry 3 }       
            
        hwVirtualAccessExterLinkDownIfOperStatus OBJECT-TYPE
            SYNTAX INTEGER
            {
                up(1),
                down(2)
            }
            MAX-ACCESS read-only
            STATUS current
            DESCRIPTION
                "Indicates link operate state.
                Options:
                1. up(1)          -indicates link operate state is up.
                2. down(2)        -indicates link operate state is down."
            ::= { hwVirtualAccessExterLinkDownEntry 4 }
        
        hwVirtualAccessExterLinkDownIfName OBJECT-TYPE
            SYNTAX SnmpAdminString
            MAX-ACCESS read-only
            STATUS current
            DESCRIPTION
                "Indicates the name of failure interface."
            ::= { hwVirtualAccessExterLinkDownEntry 5 }
			
        hwVirtualAccessExterLinkDownReason OBJECT-TYPE
            SYNTAX Integer32(1..65535)
            MAX-ACCESS read-only
            STATUS current
            DESCRIPTION
                 "This object indicates the cause that the Link becomes down.
                 Options:
                 1. ifPhysicalLinkDown(1)     --indicates interface physical link was down.
                 2. interfaceDelete(2)        --indicates interface was deleted.
                 3. ifPhysicalLinkUp(3)       --indicates interface physical link was up.
				 "
            ::= { hwVirtualAccessExterLinkDownEntry 6 }

            
            

			
        hwVirtualAccessTrap OBJECT IDENTIFIER ::= { hwVirtualAccessMib 2 }
        
        hwVirtualAccessLspTrap OBJECT IDENTIFIER ::= { hwVirtualAccessTrap 1 }

        hwVirtualAccessLspDown NOTIFICATION-TYPE
            OBJECTS { hwVirtualAccessLspId, hwVirtualAccessLspApId, hwVirtualAccessLspIfIndex, hwVirtualAccessLspIfName, hwVirtualAccessLspOperState }
            STATUS current
            DESCRIPTION 
                "This notification indicates that virtual access LSP changes to down."
            ::= { hwVirtualAccessLspTrap 1 }
        
        hwVirtualAccessLspDownClear NOTIFICATION-TYPE
            OBJECTS { hwVirtualAccessLspId, hwVirtualAccessLspApId, hwVirtualAccessLspIfIndex, hwVirtualAccessLspIfName, hwVirtualAccessLspOperState }
            STATUS current
            DESCRIPTION 
                "This notification indicates that virtual access LSP changes to up."
            ::= { hwVirtualAccessLspTrap 2 }
            
        hwVirtualAccessTunnel OBJECT IDENTIFIER ::= { hwVirtualAccessTrap 2 }
                             
        hwVirtualAccessTunnelDown NOTIFICATION-TYPE
            OBJECTS { hwVirtualAccessTunnelApAdminIp, hwVirtualAccessIfIndex, hwVirtualAccessTunnelOperState, hwVirtualAccessTunnelReason, hwVirtualAccessTunnelName, hwVirtualAccessExplicitPathName }
            STATUS current
            DESCRIPTION 
                "This notification indicates that virtual access tunnel changes to down."
            ::= { hwVirtualAccessTunnel 1 }
        
        hwVirtualAccessTunnelDownClear NOTIFICATION-TYPE
            OBJECTS { hwVirtualAccessTunnelOperState, hwVirtualAccessTunnelReason }
            STATUS current
            DESCRIPTION 
                "This notification indicates that virtual access tunnel changes to up."
            ::= { hwVirtualAccessTunnel 2 }

        hwVirtualAccessTunnelHSBSwitch NOTIFICATION-TYPE
            OBJECTS { hwVirtualAccessTunnelSourceNodeId, hwVirtualAccessTunnelDestNodeId, hwVirtualAccessTunnelId, hwVirtualAccessTunnelSwitchReason }
            STATUS current
            DESCRIPTION 
                "This notification indicates that virtual access tunnel switches to hot-standby LSP."
            ::= { hwVirtualAccessTunnel 3 }
        
        hwVirtualAccessTunnelHSBResume NOTIFICATION-TYPE
            OBJECTS { hwVirtualAccessTunnelSourceNodeId, hwVirtualAccessTunnelDestNodeId, hwVirtualAccessTunnelId }
            STATUS current
            DESCRIPTION 
                "This notification indicates that virtual access tunnel resumes from hot-standby LSP."
            ::= { hwVirtualAccessTunnel 4 }

        hwVirtualAccessTunnelReOpt NOTIFICATION-TYPE
            OBJECTS { hwVirtualAccessTunnelSourceNodeId, hwVirtualAccessTunnelDestNodeId, hwVirtualAccessTunnelId, hwVirtualAccessLspType, hwVirtualAccessLspPath, hwVirtualAccessTunnelName, hwVirtualAccessExplicitPathName }
            STATUS current
            DESCRIPTION 
                "This notification indicates that virtual access tunnel re-optimized."
            ::= { hwVirtualAccessTunnel 5 }
                                                      
       hwVirtualAccessLinkDownTrap OBJECT IDENTIFIER ::= { hwVirtualAccessTrap 3 }
       
       hwVirtualAccessLinkDown NOTIFICATION-TYPE
            OBJECTS { hwVirtualAccessLinkDownIfName, hwVirtualAccessLinkDownIfAdminStatus, hwVirtualAccessLinkDownIfOperStatus, hwVirtualAccessLinkDownReason}
            STATUS current
            DESCRIPTION 
                "This notification indicates that interface changes to down."
            ::= { hwVirtualAccessLinkDownTrap 1 }
        
       hwVirtualAccessLinkDownClear NOTIFICATION-TYPE
            OBJECTS { hwVirtualAccessLinkDownIfName, hwVirtualAccessLinkDownIfAdminStatus, hwVirtualAccessLinkDownIfOperStatus,  hwVirtualAccessLinkDownReason}
            STATUS current
            DESCRIPTION 
                "This notification indicates that interface changes to up."
            ::= { hwVirtualAccessLinkDownTrap 2 } 
              
        hwVirtualAccessExterLinkDownTrap OBJECT IDENTIFIER ::= { hwVirtualAccessTrap 4 }
        
        hwVirtualAccessExterLinkDown NOTIFICATION-TYPE
            OBJECTS { hwVirtualAccessExterLinkDownIfName, hwVirtualAccessExterLinkDownIfAdminStatus, hwVirtualAccessExterLinkDownIfOperStatus, hwVirtualAccessExterLinkDownReason}
            STATUS current
            DESCRIPTION 
                "This notification indicates that interface changes to down."
            ::= { hwVirtualAccessExterLinkDownTrap 1 }
        
       hwVirtualAccessExterLinkDownClear NOTIFICATION-TYPE
            OBJECTS { hwVirtualAccessExterLinkDownIfName, hwVirtualAccessExterLinkDownIfAdminStatus, hwVirtualAccessExterLinkDownIfOperStatus,  hwVirtualAccessExterLinkDownReason}
            STATUS current
            DESCRIPTION 
                "This notification indicates that interface changes to up."
            ::= { hwVirtualAccessExterLinkDownTrap 2 } 

       hwVirtualAccessApSelectedMasterTrap OBJECT IDENTIFIER ::= { hwVirtualAccessTrap 5 }     
       
       hwVirtualAccessApSelectedMaster NOTIFICATION-TYPE
            OBJECTS { hwVirtualAccessApIpAddress, hwVirtualAccessPrimaryMasterIpAddress, hwVirtualAccessSecondaryMasterIpAddress}
            STATUS current
            DESCRIPTION 
                "This notification indicates that the master of ap have been selected ."
            ::= { hwVirtualAccessApSelectedMasterTrap 1 }
            
       hwVirtualAccessTrapObjects OBJECT IDENTIFIER ::= { hwVirtualAccessTrap 6 }     

       hwVirtualAccessTunnelSwitchReason OBJECT-TYPE
            SYNTAX Integer32
            MAX-ACCESS read-only
            STATUS current
            DESCRIPTION
                 "This object indicates the cause that the hot-standby LSP switches.
                 Options:
                 1. PrimaryLspDown(1)                        --indicates primary LSP was down.
                 2. PrimaryBfdDown(2)                         --indicates primary BFD was down.
                 3. PrimaryLinkNumberNotSatisfy(3) --indicates the number of links on primary LSP does not meet requirements.
				 "
            ::= { hwVirtualAccessTrapObjects 1 }    
       
        hwVirtualAccessLspPath OBJECT-TYPE
            SYNTAX OCTET STRING
            MAX-ACCESS read-only
            STATUS current
            DESCRIPTION
                "Indicates the path of LSP."
            ::= { hwVirtualAccessTrapObjects 2 }

      --  Conformance information
-- 
        hwVirtualAccessTunnelMIBConformance OBJECT IDENTIFIER ::= { hwVirtualAccessInfo 2 }
        
        hwVirtualAccessTunnelMIBCompliances OBJECT IDENTIFIER ::= { hwVirtualAccessTunnelMIBConformance 1 }
        
--  this module
        hwVirtualAccessTunnelMIBCompliance MODULE-COMPLIANCE
            STATUS current
            DESCRIPTION 
                "The compliance statement for systems supporting 
                the HUAWEI-VirtualAccess-MIB."
            MODULE -- this module
                MANDATORY-GROUPS { hwVirtualAccessTunnelNotificationGroup }
            ::= { hwVirtualAccessTunnelMIBCompliances 1 }
        
        hwVirtualAccessTunnelMIBGroups OBJECT IDENTIFIER ::= { hwVirtualAccessTunnelMIBConformance 2 }
        
        hwVirtualAccessTunnelGroup OBJECT-GROUP
            OBJECTS { hwVirtualAccessLspApId, hwVirtualAccessLspIfIndex, hwVirtualAccessLspIfName, hwVirtualAccessLspOperState, hwVirtualAccessLspId, 
            hwVirtualAccessTunnelApAdminIp, hwVirtualAccessIfIndex, hwVirtualAccessTunnelOperState, hwVirtualAccessTunnelReason, 
            hwVirtualAccessLinkDownIfAdminStatus, hwVirtualAccessLinkDownIfOperStatus, hwVirtualAccessLinkDownIfName, hwVirtualAccessLinkDownReason,
            hwVirtualAccessExterLinkDownIfAdminStatus, hwVirtualAccessExterLinkDownIfOperStatus, hwVirtualAccessExterLinkDownIfName, 
            hwVirtualAccessExterLinkDownReason, hwVirtualAccessApIpAddress, hwVirtualAccessPrimaryMasterIpAddress, hwVirtualAccessSecondaryMasterIpAddress,
            hwVirtualAccessTunnelSwitchReason, hwVirtualAccessLspPath,
            hwVirtualAccessTunnelName, hwVirtualAccessExplicitPathName
            }
            STATUS current
            DESCRIPTION 
                "The virtual access tunnel group."
            ::= { hwVirtualAccessTunnelMIBGroups 1 }

        hwVirtualAccessTunnelNotificationGroup NOTIFICATION-GROUP
            NOTIFICATIONS { hwVirtualAccessLspDown, hwVirtualAccessLspDownClear, hwVirtualAccessTunnelDown, hwVirtualAccessTunnelDownClear, hwVirtualAccessTunnelHSBSwitch,
            hwVirtualAccessTunnelHSBResume, hwVirtualAccessTunnelReOpt, hwVirtualAccessLinkDown, hwVirtualAccessLinkDownClear, hwVirtualAccessExterLinkDown, hwVirtualAccessExterLinkDownClear, 
            hwVirtualAccessApSelectedMaster
            }
            STATUS current
            DESCRIPTION 
                "The virtual access tunnel Notification group."
            ::= { hwVirtualAccessTunnelMIBGroups 2 }    
     
                     
    END

--
-- HUAWEI-VIRTUALACCESS-MIB.mib
--
